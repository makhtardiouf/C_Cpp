EUTRA-RRC-Definitions DEFINITIONS AUTOMATIC TAGS ::=

BEGIN

-- ASN1STOP

BCCH-BCH-Message ::= SEQUENCE {
	message					BCCH-BCH-MessageType
}

BCCH-BCH-MessageType ::=						MasterInformationBlock

-- ASN1STOP

BCCH-DL-SCH-Message ::= SEQUENCE {
	message					BCCH-DL-SCH-MessageType
}

BCCH-DL-SCH-MessageType ::= CHOICE {
	c1						CHOICE {
		systemInformation						SystemInformation,
		systemInformationBlockType1				SystemInformationBlockType1
	},
	messageClassExtension	SEQUENCE {}
}

-- ASN1STOP

MCCH-Message ::= 		SEQUENCE {
	message					MCCH-MessageType
}

MCCH-MessageType ::= CHOICE {
	c1							CHOICE {
		mbsfnAreaConfiguration-r9		MBSFNAreaConfiguration-r9
	},
	later						CHOICE {
		c2								CHOICE{
			mbmsCountingRequest-r10			MBMSCountingRequest-r10
		},
		messageClassExtension	SEQUENCE {}
	}
}

-- ASN1STOP

PCCH-Message ::= SEQUENCE {
	message					PCCH-MessageType
}

PCCH-MessageType ::= CHOICE {
	c1						CHOICE {
		paging									Paging
	},
	messageClassExtension	SEQUENCE {}
}

-- ASN1STOP

DL-CCCH-Message ::= SEQUENCE {
	message					DL-CCCH-MessageType
}

DL-CCCH-MessageType ::= CHOICE {
	c1						CHOICE {
		rrcConnectionReestablishment			RRCConnectionReestablishment,
		rrcConnectionReestablishmentReject		RRCConnectionReestablishmentReject,
		rrcConnectionReject						RRCConnectionReject,
		rrcConnectionSetup						RRCConnectionSetup
	},
	messageClassExtension	SEQUENCE {}
}

-- ASN1STOP

DL-DCCH-Message ::= SEQUENCE {
	message					DL-DCCH-MessageType
}

DL-DCCH-MessageType ::= CHOICE {
	c1						CHOICE {
		csfbParametersResponseCDMA2000			CSFBParametersResponseCDMA2000,
		dlInformationTransfer					DLInformationTransfer,
		handoverFromEUTRAPreparationRequest		HandoverFromEUTRAPreparationRequest,
		mobilityFromEUTRACommand				MobilityFromEUTRACommand,
		rrcConnectionReconfiguration			RRCConnectionReconfiguration,
		rrcConnectionRelease					RRCConnectionRelease,
		securityModeCommand						SecurityModeCommand,
		ueCapabilityEnquiry						UECapabilityEnquiry,
		counterCheck							CounterCheck,
		ueInformationRequest-r9					UEInformationRequest-r9,
		loggedMeasurementConfiguration-r10		LoggedMeasurementConfiguration-r10,
		rnReconfiguration-r10					RNReconfiguration-r10,
		spare4 NULL,
		spare3 NULL, spare2 NULL, spare1 NULL
	},
	messageClassExtension	SEQUENCE {}
}

-- ASN1STOP

UL-CCCH-Message ::= SEQUENCE {
	message					UL-CCCH-MessageType
}

UL-CCCH-MessageType ::= CHOICE {
	c1						CHOICE {
		rrcConnectionReestablishmentRequest		RRCConnectionReestablishmentRequest,
		rrcConnectionRequest					RRCConnectionRequest
	},
	messageClassExtension	SEQUENCE {}
}

-- ASN1STOP

UL-DCCH-Message ::= SEQUENCE {
	message					UL-DCCH-MessageType
}

UL-DCCH-MessageType ::= CHOICE {
	c1						CHOICE {
		csfbParametersRequestCDMA2000			CSFBParametersRequestCDMA2000,
		measurementReport						MeasurementReport,
		rrcConnectionReconfigurationComplete	RRCConnectionReconfigurationComplete,
		rrcConnectionReestablishmentComplete	RRCConnectionReestablishmentComplete,
		rrcConnectionSetupComplete				RRCConnectionSetupComplete,
		securityModeComplete					SecurityModeComplete,
		securityModeFailure						SecurityModeFailure,
		ueCapabilityInformation					UECapabilityInformation,
		ulHandoverPreparationTransfer			ULHandoverPreparationTransfer,
		ulInformationTransfer					ULInformationTransfer,
		counterCheckResponse					CounterCheckResponse,
		ueInformationResponse-r9				UEInformationResponse-r9,
		proximityIndication-r9					ProximityIndication-r9,
		rnReconfigurationComplete-r10			RNReconfigurationComplete-r10,
		mbmsCountingResponse-r10				MBMSCountingResponse-r10,
		interFreqRSTDMeasurementIndication-r10	InterFreqRSTDMeasurementIndication-r10
	},
	messageClassExtension	CHOICE {
		c2							CHOICE {
			ueAssistanceInformation-r11			UEAssistanceInformation-r11,
			inDeviceCoexIndication-r11			InDeviceCoexIndication-r11,
			mbmsInterestIndication-r11			MBMSInterestIndication-r11,
			scgFailureInformation-r12			SCGFailureInformation-r12,
			sidelinkUEInformation-r12			SidelinkUEInformation-r12,
			spare11 NULL, spare10 NULL,
			spare9 NULL, spare8 NULL, spare7 NULL,
			spare6 NULL, spare5 NULL, spare4 NULL,
			spare3 NULL, spare2 NULL, spare1 NULL
		},
		messageClassExtensionFuture-r11	SEQUENCE {}
	}
}

-- ASN1STOP

SC-MCCH-Message ::= SEQUENCE {
	message					SC-MCCH-MessageType
}


SC-MCCH-MessageType ::= CHOICE {
	c1						CHOICE {
		scptmConfiguration-r13						SCPTMConfiguration-r13
	},
	messageClassExtension	SEQUENCE {}
}

-- ASN1STOP

CounterCheck ::=			SEQUENCE {
	rrc-TransactionIdentifier			RRC-TransactionIdentifier,
	criticalExtensions					CHOICE {
		c1									CHOICE {
			counterCheck-r8						CounterCheck-r8-IEs,
			spare3 NULL, spare2 NULL, spare1 NULL
		},
		criticalExtensionsFuture			SEQUENCE {}
	}
}

CounterCheck-r8-IEs ::=	SEQUENCE {
	drb-CountMSB-InfoList				DRB-CountMSB-InfoList,
	nonCriticalExtension				CounterCheck-v8a0-IEs				OPTIONAL
}

CounterCheck-v8a0-IEs ::= SEQUENCE {
	lateNonCriticalExtension			OCTET STRING						OPTIONAL,
	nonCriticalExtension				SEQUENCE {}							OPTIONAL
}

DRB-CountMSB-InfoList ::=		SEQUENCE (SIZE (1..maxDRB)) OF DRB-CountMSB-Info

DRB-CountMSB-Info ::=	SEQUENCE {
	drb-Identity					DRB-Identity,
	countMSB-Uplink					INTEGER(0..33554431),
	countMSB-Downlink				INTEGER(0..33554431)
}

-- ASN1STOP

CounterCheckResponse ::=			SEQUENCE {
	rrc-TransactionIdentifier			RRC-TransactionIdentifier,
	criticalExtensions					CHOICE {
		counterCheckResponse-r8				CounterCheckResponse-r8-IEs,
		criticalExtensionsFuture			SEQUENCE {}
	}
}

CounterCheckResponse-r8-IEs ::=	SEQUENCE {
	drb-CountInfoList					DRB-CountInfoList,
	nonCriticalExtension				CounterCheckResponse-v8a0-IEs		OPTIONAL
}

CounterCheckResponse-v8a0-IEs ::= SEQUENCE {
	lateNonCriticalExtension			OCTET STRING						OPTIONAL,
	nonCriticalExtension				SEQUENCE {}							OPTIONAL
}

DRB-CountInfoList ::=			SEQUENCE (SIZE (0..maxDRB)) OF DRB-CountInfo

DRB-CountInfo ::=	SEQUENCE {
	drb-Identity					DRB-Identity,
	count-Uplink					INTEGER(0..4294967295),
	count-Downlink					INTEGER(0..4294967295)
}

-- ASN1STOP

CSFBParametersRequestCDMA2000 ::= SEQUENCE {
	criticalExtensions					CHOICE {
		csfbParametersRequestCDMA2000-r8	CSFBParametersRequestCDMA2000-r8-IEs,
		criticalExtensionsFuture			SEQUENCE {}
	}
}

CSFBParametersRequestCDMA2000-r8-IEs ::= SEQUENCE {
	nonCriticalExtension				CSFBParametersRequestCDMA2000-v8a0-IEs	OPTIONAL
}

CSFBParametersRequestCDMA2000-v8a0-IEs ::= SEQUENCE {
	lateNonCriticalExtension			OCTET STRING						OPTIONAL,
	nonCriticalExtension				SEQUENCE {}							OPTIONAL
}

-- ASN1STOP

CSFBParametersResponseCDMA2000 ::= SEQUENCE {
	rrc-TransactionIdentifier			RRC-TransactionIdentifier,
	criticalExtensions						CHOICE {
		csfbParametersResponseCDMA2000-r8		CSFBParametersResponseCDMA2000-r8-IEs,
		criticalExtensionsFuture				SEQUENCE {}
	}
}

CSFBParametersResponseCDMA2000-r8-IEs ::= SEQUENCE {
	rand								RAND-CDMA2000,
	mobilityParameters					MobilityParametersCDMA2000,
	nonCriticalExtension				CSFBParametersResponseCDMA2000-v8a0-IEs	OPTIONAL
}

CSFBParametersResponseCDMA2000-v8a0-IEs ::= SEQUENCE {
	lateNonCriticalExtension			OCTET STRING						OPTIONAL,
	nonCriticalExtension				SEQUENCE {}							OPTIONAL
}

-- ASN1STOP

DLInformationTransfer ::=			SEQUENCE {
	rrc-TransactionIdentifier			RRC-TransactionIdentifier,
	criticalExtensions					CHOICE {
		c1									CHOICE {
			dlInformationTransfer-r8			DLInformationTransfer-r8-IEs,
			spare3 NULL, spare2 NULL, spare1 NULL
		},
		criticalExtensionsFuture			SEQUENCE {}
	}
}

DLInformationTransfer-r8-IEs ::=	SEQUENCE {
	dedicatedInfoType					CHOICE {
		dedicatedInfoNAS					DedicatedInfoNAS,
		dedicatedInfoCDMA2000-1XRTT			DedicatedInfoCDMA2000,
		dedicatedInfoCDMA2000-HRPD			DedicatedInfoCDMA2000
	},
	nonCriticalExtension				DLInformationTransfer-v8a0-IEs		OPTIONAL
}

DLInformationTransfer-v8a0-IEs ::= SEQUENCE {
	lateNonCriticalExtension			OCTET STRING						OPTIONAL,
	nonCriticalExtension				SEQUENCE {}							OPTIONAL
}

-- ASN1STOP

HandoverFromEUTRAPreparationRequest ::= SEQUENCE {
	rrc-TransactionIdentifier		RRC-TransactionIdentifier,
	criticalExtensions					CHOICE {
		c1									CHOICE {
			handoverFromEUTRAPreparationRequest-r8
												HandoverFromEUTRAPreparationRequest-r8-IEs,
			spare3 NULL, spare2 NULL, spare1 NULL
		},
		criticalExtensionsFuture			SEQUENCE {}
	}
}

HandoverFromEUTRAPreparationRequest-r8-IEs ::= SEQUENCE {
	cdma2000-Type					CDMA2000-Type,
	rand							RAND-CDMA2000				OPTIONAL,	-- Cond cdma2000-Type
	mobilityParameters				MobilityParametersCDMA2000	OPTIONAL,	-- Cond cdma2000-Type
	nonCriticalExtension			HandoverFromEUTRAPreparationRequest-v890-IEs	OPTIONAL
}

HandoverFromEUTRAPreparationRequest-v890-IEs ::= SEQUENCE {
	lateNonCriticalExtension		OCTET STRING				OPTIONAL,
	nonCriticalExtension			HandoverFromEUTRAPreparationRequest-v920-IEs	OPTIONAL
}

HandoverFromEUTRAPreparationRequest-v920-IEs ::= SEQUENCE {
	concurrPrepCDMA2000-HRPD-r9		BOOLEAN					OPTIONAL,	-- Cond cdma2000-Type
	nonCriticalExtension			HandoverFromEUTRAPreparationRequest-v1020-IEs	OPTIONAL
}

HandoverFromEUTRAPreparationRequest-v1020-IEs ::= SEQUENCE {
	dualRxTxRedirectIndicator-r10		ENUMERATED {true}		OPTIONAL,	-- Cond cdma2000-1XRTT
	redirectCarrierCDMA2000-1XRTT-r10	CarrierFreqCDMA2000		OPTIONAL,	-- Cond dualRxTxRedirect
	nonCriticalExtension				SEQUENCE {}				OPTIONAL
}

-- ASN1STOP

InDeviceCoexIndication-r11 ::=		SEQUENCE {
	criticalExtensions					CHOICE {
		c1									CHOICE {
			inDeviceCoexIndication-r11				InDeviceCoexIndication-r11-IEs,
			spare3 NULL, spare2 NULL, spare1 NULL
		},
		criticalExtensionsFuture			SEQUENCE {}
	}
}

InDeviceCoexIndication-r11-IEs ::=	SEQUENCE {
	affectedCarrierFreqList-r11			AffectedCarrierFreqList-r11					OPTIONAL,
	tdm-AssistanceInfo-r11				TDM-AssistanceInfo-r11						OPTIONAL,
	lateNonCriticalExtension			OCTET STRING								OPTIONAL,
	nonCriticalExtension				InDeviceCoexIndication-v11d0-IEs			OPTIONAL
}

InDeviceCoexIndication-v11d0-IEs ::=	SEQUENCE {
	ul-CA-AssistanceInfo-r11			SEQUENCE {
		affectedCarrierFreqCombList-r11	AffectedCarrierFreqCombList-r11			OPTIONAL, 
		victimSystemType-r11				VictimSystemType-r11
	}																			OPTIONAL,
	nonCriticalExtension				SEQUENCE {}								OPTIONAL
}

AffectedCarrierFreqList-r11 ::=	SEQUENCE (SIZE (1..maxFreqIDC-r11)) OF AffectedCarrierFreq-r11

AffectedCarrierFreq-r11 ::=	SEQUENCE {
	carrierFreq-r11				MeasObjectId,
	interferenceDirection-r11	ENUMERATED {eutra, other, both, spare}
}

AffectedCarrierFreqCombList-r11 ::=	SEQUENCE (SIZE (1..maxCombIDC-r11)) OF AffectedCarrierFreqComb-r11

AffectedCarrierFreqComb-r11 ::=	SEQUENCE (SIZE (2..maxServCell-r10)) OF MeasObjectId

TDM-AssistanceInfo-r11 ::=	CHOICE {
	drx-AssistanceInfo-r11				SEQUENCE {
		drx-CycleLength-r11					ENUMERATED {sf40, sf64, sf80, sf128, sf160,
												 sf256, spare2, spare1},
		drx-Offset-r11						INTEGER (0..255)	OPTIONAL,
		drx-ActiveTime-r11					ENUMERATED {sf20, sf30, sf40, sf60, sf80,
												 sf100, spare2, spare1}
	},
	idc-SubframePatternList-r11			IDC-SubframePatternList-r11,
	...
}

IDC-SubframePatternList-r11 ::=	SEQUENCE (SIZE (1..maxSubframePatternIDC-r11)) OF IDC-SubframePattern-r11

IDC-SubframePattern-r11 ::= CHOICE {
	subframePatternFDD-r11				BIT STRING (SIZE (4)),
	subframePatternTDD-r11				CHOICE {
		subframeConfig0-r11					BIT STRING (SIZE (70)),
		subframeConfig1-5-r11				BIT STRING (SIZE (10)),
		subframeConfig6-r11					BIT STRING (SIZE (60))
	},
	...
}

VictimSystemType-r11 ::= SEQUENCE {
	gps-r11 							ENUMERATED {true}				OPTIONAL,
	glonass-r11							ENUMERATED {true}				OPTIONAL,
	bds-r11								ENUMERATED {true}				OPTIONAL,
	galileo-r11 						ENUMERATED {true}				OPTIONAL,
	wlan-r11							ENUMERATED {true}				OPTIONAL,
	bluetooth-r11						ENUMERATED {true}				OPTIONAL
}

-- ASN1STOP

InterFreqRSTDMeasurementIndication-r10 ::=			SEQUENCE {
	criticalExtensions					CHOICE {
		c1									CHOICE {
			interFreqRSTDMeasurementIndication-r10	InterFreqRSTDMeasurementIndication-r10-IEs,
			spare3 NULL, spare2 NULL, spare1 NULL
		},
		criticalExtensionsFuture			SEQUENCE {}
	}
}

InterFreqRSTDMeasurementIndication-r10-IEs ::=		SEQUENCE {
	rstd-InterFreqIndication-r10		CHOICE {
		start								SEQUENCE {
			rstd-InterFreqInfoList-r10				RSTD-InterFreqInfoList-r10
		},
		stop								NULL
	},
	lateNonCriticalExtension			OCTET STRING						OPTIONAL,
	nonCriticalExtension				SEQUENCE {}							OPTIONAL
}

RSTD-InterFreqInfoList-r10 ::=	SEQUENCE (SIZE(1..maxRSTD-Freq-r10)) OF RSTD-InterFreqInfo-r10

RSTD-InterFreqInfo-r10 ::=		SEQUENCE {
	carrierFreq-r10					ARFCN-ValueEUTRA,
	measPRS-Offset-r10				INTEGER (0..39)
--	,
----	...,
--	[[	carrierFreq-v1090			ARFCN-ValueEUTRA-v9e0				OPTIONAL
--	]]
}

-- ASN1STOP

LoggedMeasurementConfiguration-r10 ::=	SEQUENCE {
	criticalExtensions					CHOICE {
		c1									CHOICE {
			loggedMeasurementConfiguration-r10		LoggedMeasurementConfiguration-r10-IEs,
			spare3 NULL, spare2 NULL, spare1 NULL
		},
		criticalExtensionsFuture				SEQUENCE {}
	}
}


LoggedMeasurementConfiguration-r10-IEs ::= SEQUENCE {		
	traceReference-r10				TraceReference-r10,
	traceRecordingSessionRef-r10	OCTET STRING (SIZE (2)),
	tce-Id-r10						OCTET STRING (SIZE (1)),
	absoluteTimeInfo-r10			AbsoluteTimeInfo-r10,
	areaConfiguration-r10			AreaConfiguration-r10		OPTIONAL,	-- Need OR
	loggingDuration-r10				LoggingDuration-r10,
	loggingInterval-r10				LoggingInterval-r10,
	nonCriticalExtension			LoggedMeasurementConfiguration-v1080-IEs	OPTIONAL
}

LoggedMeasurementConfiguration-v1080-IEs ::= SEQUENCE {
	lateNonCriticalExtension-r10	OCTET STRING						OPTIONAL,
	nonCriticalExtension			LoggedMeasurementConfiguration-v1130-IEs	OPTIONAL
}

LoggedMeasurementConfiguration-v1130-IEs ::= SEQUENCE {
	plmn-IdentityList-r11			PLMN-IdentityList3-r11		OPTIONAL,	-- Need OR
	areaConfiguration-v1130			AreaConfiguration-v1130		OPTIONAL,	-- Need OR
	nonCriticalExtension			LoggedMeasurementConfiguration-v1250-IEs	OPTIONAL
}

LoggedMeasurementConfiguration-v1250-IEs ::= SEQUENCE {
	targetMBSFN-AreaList-r12	TargetMBSFN-AreaList-r12		OPTIONAL,	-- Need OP
	nonCriticalExtension			SEQUENCE {}					OPTIONAL
}

TargetMBSFN-AreaList-r12 ::= 			SEQUENCE (SIZE (0..maxMBSFN-Area)) OF TargetMBSFN-Area-r12

TargetMBSFN-Area-r12 ::=				SEQUENCE {
	mbsfn-AreaId-r12					MBSFN-AreaId-r12		OPTIONAL,	-- Need OR
	carrierFreq-r12						ARFCN-ValueEUTRA-r9,
	...
}

-- ASN1STOP

MasterInformationBlock ::=			SEQUENCE {
	dl-Bandwidth						ENUMERATED {
											n6, n15, n25, n50, n75, n100},
	phich-Config						PHICH-Config,
	systemFrameNumber					BIT STRING (SIZE (8)),
	spare								BIT STRING (SIZE (10))
}


-- ASN1STOP

MBMSCountingRequest-r10 ::=		SEQUENCE {
	countingRequestList-r10			CountingRequestList-r10,
	lateNonCriticalExtension		OCTET STRING						OPTIONAL,
	nonCriticalExtension			SEQUENCE {}							OPTIONAL
}

CountingRequestList-r10 ::=	SEQUENCE (SIZE (1..maxServiceCount)) OF CountingRequestInfo-r10

CountingRequestInfo-r10 ::=		SEQUENCE {
	tmgi-r10							TMGI-r9,
	...
}

-- ASN1STOP

MBMSCountingResponse-r10 ::=			SEQUENCE {
	criticalExtensions					CHOICE {
		c1									CHOICE {
			countingResponse-r10				MBMSCountingResponse-r10-IEs,
			spare3 NULL, spare2 NULL, spare1 NULL
		},
		criticalExtensionsFuture			SEQUENCE {}
	}
}

MBMSCountingResponse-r10-IEs ::=	SEQUENCE {
	mbsfn-AreaIndex-r10				INTEGER (0..maxMBSFN-Area-1) 						OPTIONAL,
	countingResponseList-r10		CountingResponseList-r10			OPTIONAL,
	lateNonCriticalExtension		OCTET STRING						OPTIONAL,
	nonCriticalExtension			SEQUENCE {}							OPTIONAL
}

CountingResponseList-r10 ::=		SEQUENCE (SIZE (1..maxServiceCount)) OF CountingResponseInfo-r10

CountingResponseInfo-r10 ::=		SEQUENCE {
	countingResponseService-r10	INTEGER (0..maxServiceCount-1),
	...
}

-- ASN1STOP

MBMSInterestIndication-r11 ::=		SEQUENCE {
	criticalExtensions					CHOICE {
		c1									CHOICE {
			interestIndication-r11				MBMSInterestIndication-r11-IEs,
			spare3 NULL, spare2 NULL, spare1 NULL
		},
		criticalExtensionsFuture			SEQUENCE {}
	}
}

MBMSInterestIndication-r11-IEs ::=	SEQUENCE {
	mbms-FreqList-r11					CarrierFreqListMBMS-r11			OPTIONAL,
	mbms-Priority-r11					ENUMERATED {true}				OPTIONAL,
	lateNonCriticalExtension			OCTET STRING					OPTIONAL,
	nonCriticalExtension				MBMSInterestIndication-r13-IEs	OPTIONAL
}

MBMSInterestIndication-r13-IEs ::=	SEQUENCE {
	mbms-Services-r13					MBMSServiceList-r13				OPTIONAL,
	nonCriticalExtension				SEQUENCE {}						OPTIONAL
}

-- ASN1STOP

MBSFNAreaConfiguration-r9 ::=		SEQUENCE {
	commonSF-Alloc-r9					CommonSF-AllocPatternList-r9,
	commonSF-AllocPeriod-r9				ENUMERATED {
												rf4, rf8, rf16, rf32, rf64, rf128, rf256},
	pmch-InfoList-r9					PMCH-InfoList-r9,
	nonCriticalExtension				MBSFNAreaConfiguration-v930-IEs	OPTIONAL
}

MBSFNAreaConfiguration-v930-IEs ::= SEQUENCE {
	lateNonCriticalExtension			OCTET STRING						OPTIONAL,
	nonCriticalExtension				MBSFNAreaConfiguration-v1250-IEs		OPTIONAL
}

MBSFNAreaConfiguration-v1250-IEs ::= SEQUENCE {
	pmch-InfoListExt-r12				PMCH-InfoListExt-r12 				OPTIONAL, 	-- Need OR
	nonCriticalExtension				SEQUENCE {}							OPTIONAL
}

CommonSF-AllocPatternList-r9 ::=	SEQUENCE (SIZE (1..maxMBSFN-Allocations)) OF MBSFN-SubframeConfig

-- ASN1STOP

MeasurementReport ::=				SEQUENCE {
	criticalExtensions					CHOICE {
		c1									CHOICE{
			measurementReport-r8				MeasurementReport-r8-IEs,
			spare7 NULL,
			spare6 NULL, spare5 NULL, spare4 NULL,
			spare3 NULL, spare2 NULL, spare1 NULL
		},
		criticalExtensionsFuture			SEQUENCE {}
	}
}

MeasurementReport-r8-IEs ::=		SEQUENCE {
	measResults							MeasResults,
	nonCriticalExtension				MeasurementReport-v8a0-IEs							OPTIONAL
}

MeasurementReport-v8a0-IEs ::= SEQUENCE {
	lateNonCriticalExtension			OCTET STRING						OPTIONAL,
	nonCriticalExtension				SEQUENCE {}							OPTIONAL
}

-- ASN1STOP

MobilityFromEUTRACommand ::=		SEQUENCE {
	rrc-TransactionIdentifier			RRC-TransactionIdentifier,
	criticalExtensions					CHOICE {
		c1									CHOICE{
			mobilityFromEUTRACommand-r8		MobilityFromEUTRACommand-r8-IEs,
			mobilityFromEUTRACommand-r9 		MobilityFromEUTRACommand-r9-IEs,
			spare2 NULL, spare1 	NULL
		},
		criticalExtensionsFuture			SEQUENCE {}
	}
}

MobilityFromEUTRACommand-r8-IEs ::=	SEQUENCE {
	cs-FallbackIndicator				BOOLEAN,
	purpose								CHOICE{
		handover							Handover,
		cellChangeOrder						CellChangeOrder
	},
	nonCriticalExtension				MobilityFromEUTRACommand-v8a0-IEs	OPTIONAL
}

MobilityFromEUTRACommand-v8a0-IEs ::= SEQUENCE {
	lateNonCriticalExtension			OCTET STRING						OPTIONAL,
	nonCriticalExtension				MobilityFromEUTRACommand-v8d0-IEs	OPTIONAL
}

MobilityFromEUTRACommand-v8d0-IEs ::= SEQUENCE {
	bandIndicator						BandIndicatorGERAN			OPTIONAL,	-- Cond GERAN
	nonCriticalExtension				SEQUENCE {}					OPTIONAL
}

MobilityFromEUTRACommand-r9-IEs ::=	SEQUENCE {
	cs-FallbackIndicator				BOOLEAN,
	purpose								CHOICE{
		handover							Handover,
		cellChangeOrder						CellChangeOrder,
		e-CSFB-r9							E-CSFB-r9,
		...
	},
	nonCriticalExtension				MobilityFromEUTRACommand-v930-IEs	OPTIONAL
}

MobilityFromEUTRACommand-v930-IEs ::= SEQUENCE {
	lateNonCriticalExtension			OCTET STRING						OPTIONAL,
	nonCriticalExtension				MobilityFromEUTRACommand-v960-IEs	OPTIONAL
}

MobilityFromEUTRACommand-v960-IEs ::= SEQUENCE {
	bandIndicator						BandIndicatorGERAN			OPTIONAL,	-- Cond GERAN
	nonCriticalExtension				SEQUENCE {}					OPTIONAL
}

Handover ::=						SEQUENCE {
	targetRAT-Type						ENUMERATED {
											utra, geran, cdma2000-1XRTT, cdma2000-HRPD,
											spare4,	spare3, spare2, spare1, ...},
	targetRAT-MessageContainer			OCTET STRING,
	nas-SecurityParamFromEUTRA			OCTET STRING (SIZE (1)) 	OPTIONAL,	-- Cond UTRAGERAN
	systemInformation					SI-OrPSI-GERAN				OPTIONAL	-- Cond PSHO
}

CellChangeOrder ::=				SEQUENCE {
	t304								ENUMERATED {
											ms100, ms200, ms500, ms1000,
											ms2000, ms4000, ms8000, spare1},
	targetRAT-Type						CHOICE {
			geran							SEQUENCE {
				physCellId						PhysCellIdGERAN,
				carrierFreq						CarrierFreqGERAN,
				networkControlOrder				BIT STRING (SIZE (2)) 		OPTIONAL,	-- Need OP
				systemInformation				SI-OrPSI-GERAN				OPTIONAL	-- Need OP
			},
			...
	}
}

SI-OrPSI-GERAN ::=					CHOICE {
	si									SystemInfoListGERAN,
	psi									SystemInfoListGERAN
}

E-CSFB-r9 ::=						SEQUENCE {
	messageContCDMA2000-1XRTT-r9		OCTET STRING		OPTIONAL, 	-- Need ON
	mobilityCDMA2000-HRPD-r9			ENUMERATED {
											handover, redirection 
										}					OPTIONAL,	-- Need OP
	messageContCDMA2000-HRPD-r9		OCTET STRING		OPTIONAL, 	-- Cond concHO
	redirectCarrierCDMA2000-HRPD-r9	CarrierFreqCDMA2000	OPTIONAL	-- Cond concRedir
}

-- ASN1STOP

Paging ::=					SEQUENCE {
	pagingRecordList				PagingRecordList 					OPTIONAL,	-- Need ON
	systemInfoModification			ENUMERATED {true}					OPTIONAL,	-- Need ON
	etws-Indication					ENUMERATED {true}					OPTIONAL,	-- Need ON
	nonCriticalExtension			Paging-v890-IEs						OPTIONAL
}

Paging-v890-IEs ::=			SEQUENCE {
	lateNonCriticalExtension		OCTET STRING							OPTIONAL,
	nonCriticalExtension			Paging-v920-IEs							OPTIONAL
}

Paging-v920-IEs ::=			SEQUENCE {
	cmas-Indication-r9				ENUMERATED {true}					OPTIONAL,	-- Need ON
	nonCriticalExtension				Paging-v1130-IEs				OPTIONAL
}

Paging-v1130-IEs ::=			SEQUENCE {
	eab-ParamModification-r11		ENUMERATED {true}					OPTIONAL,	-- Need ON
	nonCriticalExtension			Paging-v13xx-IEs					OPTIONAL
}

Paging-v13xx-IEs ::=			SEQUENCE {
	redistributionIndication-r13	ENUMERATED {true}					OPTIONAL,	--Need ON
	systemInfoModification-eDRX-r13	ENUMERATED {true}					OPTIONAL,	-- Need ON
	nonCriticalExtension			SEQUENCE {}							OPTIONAL
}

PagingRecordList ::=				SEQUENCE (SIZE (1..maxPageRec)) OF PagingRecord

PagingRecord ::=					SEQUENCE {
	ue-Identity							PagingUE-Identity,
	cn-Domain							ENUMERATED	{ps, cs},
	...
}

PagingUE-Identity ::=				CHOICE {
	s-TMSI								S-TMSI,
	imsi								IMSI,
	...
}

IMSI ::=							SEQUENCE (SIZE (6..21)) OF IMSI-Digit

IMSI-Digit ::=						INTEGER (0..9)

-- ASN1STOP

ProximityIndication-r9 ::= SEQUENCE {
	criticalExtensions					CHOICE {
		c1									CHOICE {
			proximityIndication-r9				ProximityIndication-r9-IEs,
			spare3 NULL, spare2 NULL, spare1 NULL
			},
		criticalExtensionsFuture			SEQUENCE {}
	}
}

ProximityIndication-r9-IEs ::= SEQUENCE {
	type-r9								ENUMERATED {entering, leaving},
	carrierFreq-r9						CHOICE {
		eutra-r9							ARFCN-ValueEUTRA,
		utra-r9								ARFCN-ValueUTRA,
	--	...,
		eutra2-v9e0							ARFCN-ValueEUTRA-v9e0
	},
	nonCriticalExtension				ProximityIndication-v930-IEs							OPTIONAL
}

ProximityIndication-v930-IEs ::= SEQUENCE {
	lateNonCriticalExtension			OCTET STRING						OPTIONAL,
	nonCriticalExtension				SEQUENCE {}							OPTIONAL
}

-- ASN1STOP

RNReconfiguration-r10 ::=		SEQUENCE {
	rrc-TransactionIdentifier		RRC-TransactionIdentifier,
	criticalExtensions				CHOICE {
		c1								CHOICE {
			rnReconfiguration-r10		RNReconfiguration-r10-IEs, 
			spare3 NULL, spare2 NULL, spare1 NULL
		},
		criticalExtensionsFuture		SEQUENCE {}
	}
}

RNReconfiguration-r10-IEs ::=		SEQUENCE {
	rn-SystemInfo-r10					RN-SystemInfo-r10			OPTIONAL,	-- Need ON
	rn-SubframeConfig-r10				RN-SubframeConfig-r10			OPTIONAL,	-- Need ON
	lateNonCriticalExtension			OCTET STRING					OPTIONAL,
	nonCriticalExtension				SEQUENCE {}						OPTIONAL
}

RN-SystemInfo-r10 ::=			SEQUENCE {
	systemInformationBlockType1-r10		OCTET STRING (CONTAINING SystemInformationBlockType1)	OPTIONAL,	-- Need ON
	systemInformationBlockType2-r10		SystemInformationBlockType2		OPTIONAL,	-- Need ON
	...
}

-- ASN1STOP

RNReconfigurationComplete-r10 ::=		SEQUENCE {
	rrc-TransactionIdentifier				RRC-TransactionIdentifier,
	criticalExtensions						CHOICE {
		c1										CHOICE{
			rnReconfigurationComplete-r10			RNReconfigurationComplete-r10-IEs,
			spare3 NULL, spare2 NULL, spare1 NULL
		},
		criticalExtensionsFuture				SEQUENCE {}
	}
}

RNReconfigurationComplete-r10-IEs ::=	SEQUENCE {
	lateNonCriticalExtension				OCTET STRING				OPTIONAL,
	nonCriticalExtension					SEQUENCE {}					OPTIONAL
}

-- ASN1STOP

RRCConnectionReconfiguration ::=	SEQUENCE {
	rrc-TransactionIdentifier			RRC-TransactionIdentifier,
	criticalExtensions					CHOICE {
		c1									CHOICE{
			rrcConnectionReconfiguration-r8		RRCConnectionReconfiguration-r8-IEs,
			spare7 NULL,
			spare6 NULL, spare5 NULL, spare4 NULL,
			spare3 NULL, spare2 NULL, spare1 NULL
		},
		criticalExtensionsFuture			SEQUENCE {}
	}
}

RRCConnectionReconfiguration-r8-IEs ::= SEQUENCE {
	measConfig							MeasConfig						OPTIONAL,	-- Need ON
	mobilityControlInfo					MobilityControlInfo				OPTIONAL,	-- Cond HO
	dedicatedInfoNASList				SEQUENCE (SIZE(1..maxDRB)) OF
											DedicatedInfoNAS			OPTIONAL,	-- Cond nonHO
	radioResourceConfigDedicated		RadioResourceConfigDedicated	OPTIONAL, -- Cond HO-toEUTRA
	securityConfigHO					SecurityConfigHO				OPTIONAL,	-- Cond HO
	nonCriticalExtension				RRCConnectionReconfiguration-v890-IEs	OPTIONAL
}

RRCConnectionReconfiguration-v890-IEs ::= SEQUENCE {
	lateNonCriticalExtension			OCTET STRING (CONTAINING RRCConnectionReconfiguration-v8m0-IEs)	OPTIONAL,
	nonCriticalExtension				RRCConnectionReconfiguration-v920-IEs	OPTIONAL
}

-- Late non-critical extensions:
RRCConnectionReconfiguration-v8m0-IEs ::= SEQUENCE {
	-- Following field is only for pre REL-10 late non-critical extensions
	lateNonCriticalExtension			OCTET STRING					OPTIONAL, 
	nonCriticalExtension				RRCConnectionReconfiguration-v10i0-IEs		OPTIONAL
}

RRCConnectionReconfiguration-v10i0-IEs ::= SEQUENCE {
	antennaInfoDedicatedPCell-v10i0		AntennaInfoDedicated-v10i0			OPTIONAL,	-- Need ON
	-- Following field is only for late non-critical extensions from REL-10
	nonCriticalExtension				SEQUENCE {}				OPTIONAL
}

-- Regular non-critical extensions:
RRCConnectionReconfiguration-v920-IEs ::= SEQUENCE {
	otherConfig-r9						OtherConfig-r9					OPTIONAL,	-- Need ON
	fullConfig-r9						ENUMERATED {true}				OPTIONAL,	-- Cond HO-Reestab
	nonCriticalExtension				RRCConnectionReconfiguration-v1020-IEs	OPTIONAL
}

RRCConnectionReconfiguration-v1020-IEs ::= SEQUENCE {
	sCellToReleaseList-r10				SCellToReleaseList-r10			OPTIONAL,	-- Need ON
	sCellToAddModList-r10				SCellToAddModList-r10			OPTIONAL,	-- Need ON
	nonCriticalExtension				RRCConnectionReconfiguration-v1130-IEs	OPTIONAL
}

RRCConnectionReconfiguration-v1130-IEs ::= SEQUENCE {
	systemInfomationBlockType1Dedicated-r11	OCTET STRING (CONTAINING SystemInformationBlockType1)																			OPTIONAL,	-- Need ON
	nonCriticalExtension				RRCConnectionReconfiguration-v1250-IEs	OPTIONAL
}

RRCConnectionReconfiguration-v1250-IEs ::= SEQUENCE {
	wlan-OffloadInfo-r12				CHOICE {
		release 								NULL,
		setup									SEQUENCE {
			wlan-OffloadConfigDedicated-r12		WLAN-OffloadConfig-r12,
			t350-r12								ENUMERATED {min5, min10, min20, min30, min60,
												 min120, min180, spare1}	OPTIONAL	-- Need OR
		}
	}																	OPTIONAL,		-- Need ON
	scg-Configuration-r12				SCG-Configuration-r12		OPTIONAL, 	-- Cond nonFullConfig
	sl-SyncTxControl-r12				SL-SyncTxControl-r12			OPTIONAL,	-- Need ON
	sl-DiscConfig-r12					SL-DiscConfig-r12				OPTIONAL,	-- Need ON
	sl-CommConfig-r12					SL-CommConfig-r12				OPTIONAL,	-- Need ON
	nonCriticalExtension				RRCConnectionReconfiguration-v13xy-IEs	OPTIONAL
}

RRCConnectionReconfiguration-v13xy-IEs ::= SEQUENCE {
	sCellToReleaseListExt-r13			SCellToReleaseListExt-r13		OPTIONAL,	-- Need ON
	sCellToAddModListExt-r13			SCellToAddModListExt-r13		OPTIONAL,	-- Need ON
	nonCriticalExtension				SEQUENCE {}						OPTIONAL
}

SL-SyncTxControl-r12 ::=			SEQUENCE {
	networkControlledSyncTx-r12				ENUMERATED {on, off}		OPTIONAL		-- Need OP
}

PSCellToAddMod-r12 ::=				SEQUENCE {
	sCellIndex-r12						SCellIndex-r10,
	cellIdentification-r12				SEQUENCE {
		physCellId-r12						PhysCellId,
		dl-CarrierFreq-r12					ARFCN-ValueEUTRA-r9
	}																	OPTIONAL,	-- Cond SCellAdd
	radioResourceConfigCommonPSCell-r12		RadioResourceConfigCommonPSCell-r12	OPTIONAL,	-- Cond SCellAdd
	radioResourceConfigDedicatedPSCell-r12	RadioResourceConfigDedicatedPSCell-r12	OPTIONAL, -- Cond SCellAdd2
----	...,
--	[[	
        antennaInfoDedicatedPSCell-v1280		AntennaInfoDedicated-v10i0	OPTIONAL, -- Need ON
--	]],
--	[[	
        sCellIndex-r13					SCellIndex-r13	OPTIONAL		-- Need ON
--	]]
}

PowerCoordinationInfo-r12 ::= SEQUENCE {
	p-MeNB-r12							INTEGER (1..16),
	p-SeNB-r12							INTEGER (1..16),
	powerControlMode-r12				INTEGER (1..2)
}

SCellToAddModList-r10 ::=		SEQUENCE (SIZE (1..maxSCell-r10)) OF SCellToAddMod-r10

SCellToAddModListExt-r13 ::=	SEQUENCE (SIZE (maxSCell-Plus1..maxSCell-r13)) OF SCellToAddMod-r13

SCellToAddMod-r10 ::=			SEQUENCE {
	sCellIndex-r10						SCellIndex-r10,
	cellIdentification-r10				SEQUENCE {
		physCellId-r10						PhysCellId,
		dl-CarrierFreq-r10					ARFCN-ValueEUTRA
	}																OPTIONAL,	-- Cond SCellAdd
	radioResourceConfigCommonSCell-r10		RadioResourceConfigCommonSCell-r10	OPTIONAL,	-- Cond SCellAdd
	radioResourceConfigDedicatedSCell-r10	RadioResourceConfigDedicatedSCell-r10	OPTIONAL--,	
	-- Cond SCellAdd2
--	...,
--	[[	dl-CarrierFreq-v1090				ARFCN-ValueEUTRA-v9e0	OPTIONAL	
-- Cond EARFCN-max
--	]],
--	[[	antennaInfoDedicatedSCell-v10i0		AntennaInfoDedicated-v10i0	OPTIONAL	
-- Need ON
--	]]
}

SCellToAddMod-r13 ::=			SEQUENCE {
	sCellIndex-v13xy						SCellIndex-v13xy,
	cellIdentification-r13				SEQUENCE {
		physCellId-r13						PhysCellId,
		dl-CarrierFreq-r13					ARFCN-ValueEUTRA-r9
	}																OPTIONAL,	-- Cond SCellAdd
	radioResourceConfigCommonSCell-r13		RadioResourceConfigCommonSCell-r10	OPTIONAL,	-- Cond SCellAdd
	radioResourceConfigDedicatedSCell-r13	RadioResourceConfigDedicatedSCell-r10	OPTIONAL	-- Cond SCellAdd2
}

SCellToReleaseList-r10 ::=			SEQUENCE (SIZE (1..maxSCell-r10)) OF SCellIndex-r10

SCellToReleaseListExt-r13 ::=			SEQUENCE (SIZE (maxSCell-Plus1..maxSCell-r13)) OF SCellIndex-v13xy

SCG-Configuration-r12 ::=			CHOICE {
	release								NULL,
	setup								SEQUENCE {
		scg-ConfigPartMCG-r12				SEQUENCE {
			scg-Counter-r12						INTEGER (0.. 65535)			OPTIONAL,	-- Need ON
			powerCoordinationInfo-r12			PowerCoordinationInfo-r12	OPTIONAL,	-- Need ON
			...
		}																OPTIONAL,	-- Need ON
		scg-ConfigPartSCG-r12				SCG-ConfigPartSCG-r12 		OPTIONAL	-- Need ON
	}
}

SCG-ConfigPartSCG-r12 ::=			SEQUENCE {
	radioResourceConfigDedicatedSCG-r12	RadioResourceConfigDedicatedSCG-r12	OPTIONAL,	-- Need ON
	sCellToReleaseListSCG-r12			SCellToReleaseList-r10		OPTIONAL,	-- Need ON
	pSCellToAddMod-r12					PSCellToAddMod-r12			OPTIONAL,	-- Need ON
	sCellToAddModListSCG-r12			SCellToAddModList-r10		OPTIONAL,	-- Need ON
	mobilityControlInfoSCG-r12			MobilityControlInfoSCG-r12	OPTIONAL --,
	-- Need ON
--	...,
--	[[
--	sCellToReleaseListSCG-Ext-r13			SCellToReleaseListExt-r13		OPTIONAL,	
-- Need ON
--	sCellToAddModListSCG-Ext-r13				SCellToAddModListExt-r13	OPTIONAL	
-- Need ON
--	]]
}

SecurityConfigHO ::=				SEQUENCE {
	handoverType						CHOICE {
		intraLTE							SEQUENCE {
			securityAlgorithmConfig				SecurityAlgorithmConfig		OPTIONAL,	-- Cond fullConfig
			keyChangeIndicator					BOOLEAN,
			nextHopChainingCount				NextHopChainingCount
		},
		interRAT							SEQUENCE {
			securityAlgorithmConfig				SecurityAlgorithmConfig,
			nas-SecurityParamToEUTRA			OCTET STRING (SIZE(6))
		}
	},
	...
}


-- ASN1STOP

RRCConnectionReconfigurationComplete ::= SEQUENCE {
	rrc-TransactionIdentifier			RRC-TransactionIdentifier,
	criticalExtensions					CHOICE {
		rrcConnectionReconfigurationComplete-r8
											RRCConnectionReconfigurationComplete-r8-IEs,
		criticalExtensionsFuture			SEQUENCE {}
	}
}

RRCConnectionReconfigurationComplete-r8-IEs ::= SEQUENCE {
	nonCriticalExtension				RRCConnectionReconfigurationComplete-v8a0-IEs	OPTIONAL
}

RRCConnectionReconfigurationComplete-v8a0-IEs ::= SEQUENCE {
	lateNonCriticalExtension			OCTET STRING						OPTIONAL,
	nonCriticalExtension				RRCConnectionReconfigurationComplete-v1020-IEs	OPTIONAL
}

RRCConnectionReconfigurationComplete-v1020-IEs ::= SEQUENCE {
	rlf-InfoAvailable-r10				ENUMERATED {true}				OPTIONAL,
	logMeasAvailable-r10				ENUMERATED {true}				OPTIONAL,
	nonCriticalExtension				RRCConnectionReconfigurationComplete-v1130-IEs	OPTIONAL
}

RRCConnectionReconfigurationComplete-v1130-IEs ::= SEQUENCE {
	connEstFailInfoAvailable-r11		ENUMERATED {true}				OPTIONAL,
	nonCriticalExtension				RRCConnectionReconfigurationComplete-v1250-IEs	OPTIONAL
}

RRCConnectionReconfigurationComplete-v1250-IEs ::= SEQUENCE {
	logMeasAvailableMBSFN-r12			ENUMERATED {true}				OPTIONAL,
	nonCriticalExtension				SEQUENCE {}						OPTIONAL
}

-- ASN1STOP

RRCConnectionReestablishment ::=	SEQUENCE {
	rrc-TransactionIdentifier			RRC-TransactionIdentifier,
	criticalExtensions					CHOICE {
		c1									CHOICE{
			rrcConnectionReestablishment-r8		RRCConnectionReestablishment-r8-IEs,
			spare7 NULL,
			spare6 NULL, spare5 NULL, spare4 	NULL,
			spare3 NULL, spare2 NULL, spare1 	NULL
		},
		criticalExtensionsFuture			SEQUENCE {}
	}
}

RRCConnectionReestablishment-r8-IEs ::= SEQUENCE {
	radioResourceConfigDedicated		RadioResourceConfigDedicated,
	nextHopChainingCount				NextHopChainingCount,
	nonCriticalExtension				RRCConnectionReestablishment-v8a0-IEs	OPTIONAL
}

RRCConnectionReestablishment-v8a0-IEs ::= SEQUENCE {
	lateNonCriticalExtension			OCTET STRING						OPTIONAL,
	nonCriticalExtension				SEQUENCE {}							OPTIONAL
}

-- ASN1STOP

RRCConnectionReestablishmentComplete ::= SEQUENCE {
	rrc-TransactionIdentifier			RRC-TransactionIdentifier,
	criticalExtensions					CHOICE {
		rrcConnectionReestablishmentComplete-r8
											RRCConnectionReestablishmentComplete-r8-IEs,
		criticalExtensionsFuture			SEQUENCE {}
	}
}

RRCConnectionReestablishmentComplete-r8-IEs ::= SEQUENCE {
	nonCriticalExtension				RRCConnectionReestablishmentComplete-v920-IEs	OPTIONAL
}

RRCConnectionReestablishmentComplete-v920-IEs ::= SEQUENCE {
	rlf-InfoAvailable-r9				ENUMERATED {true}				OPTIONAL,
	nonCriticalExtension				RRCConnectionReestablishmentComplete-v8a0-IEs	OPTIONAL
}

RRCConnectionReestablishmentComplete-v8a0-IEs ::= SEQUENCE {
	lateNonCriticalExtension			OCTET STRING						OPTIONAL,
	nonCriticalExtension				RRCConnectionReestablishmentComplete-v1020-IEs	OPTIONAL
}

RRCConnectionReestablishmentComplete-v1020-IEs ::= SEQUENCE {
	logMeasAvailable-r10				ENUMERATED {true}				OPTIONAL,
	nonCriticalExtension				RRCConnectionReestablishmentComplete-v1130-IEs	OPTIONAL
}

RRCConnectionReestablishmentComplete-v1130-IEs ::= SEQUENCE {
	connEstFailInfoAvailable-r11		ENUMERATED {true}				OPTIONAL,
	nonCriticalExtension				RRCConnectionReestablishmentComplete-v1250-IEs	OPTIONAL
}

RRCConnectionReestablishmentComplete-v1250-IEs ::= SEQUENCE {
	logMeasAvailableMBSFN-r12			ENUMERATED {true}				OPTIONAL,
	nonCriticalExtension				SEQUENCE {}						OPTIONAL
}

-- ASN1STOP

RRCConnectionReestablishmentReject ::= SEQUENCE {
	criticalExtensions					CHOICE {
		rrcConnectionReestablishmentReject-r8
											RRCConnectionReestablishmentReject-r8-IEs,
		criticalExtensionsFuture			SEQUENCE {}
	}
}

RRCConnectionReestablishmentReject-r8-IEs ::= SEQUENCE {
	nonCriticalExtension				RRCConnectionReestablishmentReject-v8a0-IEs	OPTIONAL
}

RRCConnectionReestablishmentReject-v8a0-IEs ::= SEQUENCE {
	lateNonCriticalExtension			OCTET STRING						OPTIONAL,
	nonCriticalExtension				SEQUENCE {}							OPTIONAL
}

-- ASN1STOP

RRCConnectionReestablishmentRequest ::= SEQUENCE {
	criticalExtensions					CHOICE {
		rrcConnectionReestablishmentRequest-r8
											RRCConnectionReestablishmentRequest-r8-IEs,
		criticalExtensionsFuture			SEQUENCE {}
	}
}

RRCConnectionReestablishmentRequest-r8-IEs ::= SEQUENCE {
	ue-Identity							ReestabUE-Identity,
	reestablishmentCause				ReestablishmentCause,
	spare								BIT STRING (SIZE (2))
}

ReestabUE-Identity ::=				SEQUENCE {
	c-RNTI								C-RNTI,
	physCellId							PhysCellId,
	shortMAC-I							ShortMAC-I
}

ReestablishmentCause ::=			ENUMERATED {
										reconfigurationFailure, handoverFailure,
										otherFailure, spare1}

-- ASN1STOP

RRCConnectionReject ::=				SEQUENCE {
	criticalExtensions					CHOICE {
		c1									CHOICE {
			rrcConnectionReject-r8				RRCConnectionReject-r8-IEs,
			spare3 NULL, spare2 NULL, spare1 NULL
		},
		criticalExtensionsFuture			SEQUENCE {}
	}
}

RRCConnectionReject-r8-IEs ::=		SEQUENCE {
	waitTime							INTEGER (1..16),
	nonCriticalExtension				RRCConnectionReject-v8a0-IEs		OPTIONAL
}

RRCConnectionReject-v8a0-IEs ::= SEQUENCE {
	lateNonCriticalExtension			OCTET STRING						OPTIONAL,
	nonCriticalExtension				RRCConnectionReject-v1020-IEs		OPTIONAL
}

RRCConnectionReject-v1020-IEs ::=	SEQUENCE {
	extendedWaitTime-r10				INTEGER (1..1800)					OPTIONAL,	-- Need ON
	nonCriticalExtension				RRCConnectionReject-v1130-IEs		OPTIONAL
}

RRCConnectionReject-v1130-IEs ::=	SEQUENCE {
	deprioritisationReq-r11				SEQUENCE {
		deprioritisationType-r11			ENUMERATED {frequency, e-utra},
		deprioritisationTimer-r11			ENUMERATED {min5, min10, min15, min30}
	}																		OPTIONAL,	-- Need ON
	nonCriticalExtension				SEQUENCE {}							OPTIONAL
}

-- ASN1STOP

RRCConnectionRelease ::=			SEQUENCE {
	rrc-TransactionIdentifier			RRC-TransactionIdentifier,
	criticalExtensions					CHOICE {
		c1									CHOICE {
			rrcConnectionRelease-r8				RRCConnectionRelease-r8-IEs,
			spare3 NULL, spare2 NULL, spare1 NULL
		},
		criticalExtensionsFuture			SEQUENCE {}
	}
}

RRCConnectionRelease-r8-IEs ::=		SEQUENCE {
	releaseCause						ReleaseCause,
	redirectedCarrierInfo				RedirectedCarrierInfo				OPTIONAL,	-- Need ON
	idleModeMobilityControlInfo			IdleModeMobilityControlInfo			OPTIONAL,	-- Need OP
	nonCriticalExtension				RRCConnectionRelease-v890-IEs		OPTIONAL
}

RRCConnectionRelease-v890-IEs ::=	SEQUENCE {
	lateNonCriticalExtension			OCTET STRING (CONTAINING RRCConnectionRelease-v9e0-IEs)	OPTIONAL,
	nonCriticalExtension				RRCConnectionRelease-v920-IEs		OPTIONAL
}

-- Late non critical extensions
RRCConnectionRelease-v9e0-IEs ::= SEQUENCE {
	redirectedCarrierInfo-v9e0			RedirectedCarrierInfo-v9e0			OPTIONAL,	-- Cond NoRedirect-r8
	idleModeMobilityControlInfo-v9e0	IdleModeMobilityControlInfo-v9e0	OPTIONAL,	-- Cond IdleInfoEUTRA
	nonCriticalExtension				SEQUENCE {}							OPTIONAL
}

-- Regular non critical extensions
RRCConnectionRelease-v920-IEs ::=	SEQUENCE {
	cellInfoList-r9					CHOICE {
		geran-r9						CellInfoListGERAN-r9,
		utra-FDD-r9						CellInfoListUTRA-FDD-r9,
		utra-TDD-r9						CellInfoListUTRA-TDD-r9,
	--	...,
		utra-TDD-r10					CellInfoListUTRA-TDD-r10
	}															OPTIONAL,	-- Cond Redirection
	nonCriticalExtension			RRCConnectionRelease-v1020-IEs		OPTIONAL
}

RRCConnectionRelease-v1020-IEs ::=	SEQUENCE {
	extendedWaitTime-r10				INTEGER (1..1800)		OPTIONAL,	-- Need ON
	nonCriticalExtension			SEQUENCE {}				OPTIONAL
}

ReleaseCause ::=				ENUMERATED {loadBalancingTAUrequired,
											other, cs-FallbackHighPriority-v1020, spare1}

RedirectedCarrierInfo ::=			CHOICE {
	eutra								ARFCN-ValueEUTRA,
	geran								CarrierFreqsGERAN,
	utra-FDD							ARFCN-ValueUTRA,
	utra-TDD							ARFCN-ValueUTRA,
	cdma2000-HRPD						CarrierFreqCDMA2000,
	cdma2000-1xRTT						CarrierFreqCDMA2000,
--	...,
	utra-TDD-r10						CarrierFreqListUTRA-TDD-r10
}

RedirectedCarrierInfo-v9e0 ::=			SEQUENCE {
	eutra-v9e0								ARFCN-ValueEUTRA-v9e0
}

CarrierFreqListUTRA-TDD-r10 ::=			SEQUENCE (SIZE (1..maxFreqUTRA-TDD-r10)) OF ARFCN-ValueUTRA

IdleModeMobilityControlInfo ::=		SEQUENCE {
	freqPriorityListEUTRA				FreqPriorityListEUTRA			OPTIONAL,		-- Need ON
	freqPriorityListGERAN				FreqsPriorityListGERAN			OPTIONAL,		-- Need ON
	freqPriorityListUTRA-FDD			FreqPriorityListUTRA-FDD		OPTIONAL,		-- Need ON
	freqPriorityListUTRA-TDD			FreqPriorityListUTRA-TDD		OPTIONAL,		-- Need ON
	bandClassPriorityListHRPD			BandClassPriorityListHRPD		OPTIONAL,		-- Need ON
	bandClassPriorityList1XRTT			BandClassPriorityList1XRTT		OPTIONAL,		-- Need ON
	t320								ENUMERATED {
											min5, min10, min20, min30, min60, min120, min180,
											spare1}						OPTIONAL--,		
											-- Need OR
--	...,
--	[[	freqPriorityListExtEUTRA-r12		FreqPriorityListExtEUTRA-r12		OPTIONAL		
-- Need ON
--	]],
--	[[	freqPriorityListEUTRA-v13xy			FreqPriorityListEUTRA-v13xy			OPTIONAL,		
-- Need ON
--		freqPriorityListExtEUTRA-v13xy		FreqPriorityListExtEUTRA-v13xy		OPTIONAL		
-- Need ON
--	]]
}

IdleModeMobilityControlInfo-v9e0 ::=	SEQUENCE {
	freqPriorityListEUTRA-v9e0			SEQUENCE (SIZE (1..maxFreq)) OF FreqPriorityEUTRA-v9e0
}

FreqPriorityListEUTRA ::=			SEQUENCE (SIZE (1..maxFreq)) OF FreqPriorityEUTRA

FreqPriorityListExtEUTRA-r12 ::=		SEQUENCE (SIZE (1..maxFreq)) OF FreqPriorityEUTRA-r12

FreqPriorityListEUTRA-v13xy ::=			SEQUENCE (SIZE (1..maxFreq)) OF FreqPriorityEUTRA-v13xy

FreqPriorityListExtEUTRA-v13xy ::=		SEQUENCE (SIZE (1..maxFreq)) OF FreqPriorityEUTRA-v13xy

FreqPriorityEUTRA ::=				SEQUENCE {
	carrierFreq							ARFCN-ValueEUTRA,
	cellReselectionPriority				CellReselectionPriority
}

FreqPriorityEUTRA-v9e0 ::=			SEQUENCE {
	carrierFreq-v9e0					ARFCN-ValueEUTRA-v9e0		OPTIONAL	-- Cond EARFCN-max
}

FreqPriorityEUTRA-r12 ::=				SEQUENCE {
	carrierFreq-r12							ARFCN-ValueEUTRA-r9,
	cellReselectionPriority-r12				CellReselectionPriority
}

FreqPriorityEUTRA-v13xy ::=				SEQUENCE {
	cellReselectionSubPriority-r13				CellReselectionSubPriority-r13 		OPTIONAL		-- Need ON
}

FreqsPriorityListGERAN ::=			SEQUENCE (SIZE (1..maxGNFG)) OF FreqsPriorityGERAN

FreqsPriorityGERAN ::=				SEQUENCE {
	carrierFreqs						CarrierFreqsGERAN,
	cellReselectionPriority				CellReselectionPriority
}

FreqPriorityListUTRA-FDD ::=		SEQUENCE (SIZE (1..maxUTRA-FDD-Carrier)) OF FreqPriorityUTRA-FDD

FreqPriorityUTRA-FDD ::=			SEQUENCE {
	carrierFreq							ARFCN-ValueUTRA,
	cellReselectionPriority				CellReselectionPriority
}

FreqPriorityListUTRA-TDD ::=		SEQUENCE (SIZE (1..maxUTRA-TDD-Carrier)) OF FreqPriorityUTRA-TDD

FreqPriorityUTRA-TDD ::=			SEQUENCE {
	carrierFreq							ARFCN-ValueUTRA,
	cellReselectionPriority				CellReselectionPriority
}

BandClassPriorityListHRPD ::=		SEQUENCE (SIZE (1..maxCDMA-BandClass)) OF BandClassPriorityHRPD

BandClassPriorityHRPD ::=			SEQUENCE {
	bandClass							BandclassCDMA2000,
	cellReselectionPriority				CellReselectionPriority
}

BandClassPriorityList1XRTT ::=	SEQUENCE (SIZE (1..maxCDMA-BandClass)) OF BandClassPriority1XRTT

BandClassPriority1XRTT ::=			SEQUENCE {
	bandClass							BandclassCDMA2000,
	cellReselectionPriority				CellReselectionPriority
}

CellInfoListGERAN-r9 ::=		SEQUENCE (SIZE (1..maxCellInfoGERAN-r9)) OF CellInfoGERAN-r9

CellInfoGERAN-r9 ::=				SEQUENCE {
	physCellId-r9						PhysCellIdGERAN,
	carrierFreq-r9						CarrierFreqGERAN,
	systemInformation-r9				SystemInfoListGERAN
}

CellInfoListUTRA-FDD-r9 ::=			SEQUENCE (SIZE (1..maxCellInfoUTRA-r9)) OF CellInfoUTRA-FDD-r9

CellInfoUTRA-FDD-r9 ::=				SEQUENCE {
	physCellId-r9						PhysCellIdUTRA-FDD,
	utra-BCCH-Container-r9				OCTET STRING
}

CellInfoListUTRA-TDD-r9 ::=			SEQUENCE (SIZE (1..maxCellInfoUTRA-r9)) OF CellInfoUTRA-TDD-r9

CellInfoUTRA-TDD-r9 ::=				SEQUENCE {
	physCellId-r9						PhysCellIdUTRA-TDD,
	utra-BCCH-Container-r9				OCTET STRING
}

CellInfoListUTRA-TDD-r10 ::=		SEQUENCE (SIZE (1..maxCellInfoUTRA-r9)) OF CellInfoUTRA-TDD-r10

CellInfoUTRA-TDD-r10 ::=			SEQUENCE {
	physCellId-r10						PhysCellIdUTRA-TDD,
	carrierFreq-r10						ARFCN-ValueUTRA,
	utra-BCCH-Container-r10				OCTET STRING
}

-- ASN1STOP

RRCConnectionRequest ::=			SEQUENCE {
	criticalExtensions					CHOICE {
		rrcConnectionRequest-r8				RRCConnectionRequest-r8-IEs,
		criticalExtensionsFuture			SEQUENCE {}
	}
}

RRCConnectionRequest-r8-IEs ::=		SEQUENCE {
	ue-Identity							InitialUE-Identity,
	establishmentCause					EstablishmentCause,
	spare								BIT STRING (SIZE (1))
}

InitialUE-Identity ::=				CHOICE {
	s-TMSI								S-TMSI,
	randomValue							BIT STRING (SIZE (40))
}

EstablishmentCause ::=				ENUMERATED {
										emergency, highPriorityAccess, mt-Access, mo-Signalling,
										mo-Data, delayTolerantAccess-v1020, mo-VoiceCall-v1280, spare1}

-- ASN1STOP

RRCConnectionSetup ::=				SEQUENCE {
	rrc-TransactionIdentifier			RRC-TransactionIdentifier,
	criticalExtensions					CHOICE {
		c1									CHOICE {
			rrcConnectionSetup-r8				RRCConnectionSetup-r8-IEs,
			spare7 NULL,
			spare6 NULL, spare5 NULL, spare4 NULL,
			spare3 NULL, spare2 NULL, spare1 NULL
		},
		criticalExtensionsFuture			SEQUENCE {}
	}
}

RRCConnectionSetup-r8-IEs ::=		SEQUENCE {
	radioResourceConfigDedicated		RadioResourceConfigDedicated,
	nonCriticalExtension				RRCConnectionSetup-v8a0-IEs			OPTIONAL
}

RRCConnectionSetup-v8a0-IEs ::= SEQUENCE {
	lateNonCriticalExtension			OCTET STRING						OPTIONAL,
	nonCriticalExtension				SEQUENCE {}							OPTIONAL
}

-- ASN1STOP

RRCConnectionSetupComplete ::=		SEQUENCE {
	rrc-TransactionIdentifier			RRC-TransactionIdentifier,
	criticalExtensions					CHOICE {
		c1									CHOICE{
			rrcConnectionSetupComplete-r8		RRCConnectionSetupComplete-r8-IEs,
			spare3 NULL, spare2 NULL, spare1 NULL
		},
		criticalExtensionsFuture			SEQUENCE {}
	}
}

RRCConnectionSetupComplete-r8-IEs ::= SEQUENCE {
	selectedPLMN-Identity				INTEGER (1..maxPLMN-r11),
	registeredMME						RegisteredMME						OPTIONAL,
	dedicatedInfoNAS					DedicatedInfoNAS,
	nonCriticalExtension				RRCConnectionSetupComplete-v8a0-IEs	OPTIONAL
}

RRCConnectionSetupComplete-v8a0-IEs ::= SEQUENCE {
	lateNonCriticalExtension			OCTET STRING						OPTIONAL,
	nonCriticalExtension				RRCConnectionSetupComplete-v1020-IEs	OPTIONAL
}

RRCConnectionSetupComplete-v1020-IEs ::= SEQUENCE {
	gummei-Type-r10						ENUMERATED {native, mapped}			OPTIONAL,
	rlf-InfoAvailable-r10				ENUMERATED {true}					OPTIONAL,
	logMeasAvailable-r10				ENUMERATED {true}					OPTIONAL,
	rn-SubframeConfigReq-r10			ENUMERATED {required, notRequired}	OPTIONAL,
	nonCriticalExtension				RRCConnectionSetupComplete-v1130-IEs	OPTIONAL
}

RRCConnectionSetupComplete-v1130-IEs ::= SEQUENCE {
	connEstFailInfoAvailable-r11		ENUMERATED {true}				OPTIONAL,
	nonCriticalExtension				RRCConnectionSetupComplete-v1250-IEs		OPTIONAL
}

RRCConnectionSetupComplete-v1250-IEs ::= SEQUENCE {
	mobilityState-r12					ENUMERATED {normal, medium, high, spare}	OPTIONAL,
	mobilityHistoryAvail-r12			ENUMERATED {true}				OPTIONAL,
	logMeasAvailableMBSFN-r12			ENUMERATED {true}				OPTIONAL,
	nonCriticalExtension				SEQUENCE {}						OPTIONAL
}

RegisteredMME ::=					SEQUENCE {
	plmn-Identity						PLMN-Identity						OPTIONAL,
	mmegi								BIT STRING (SIZE (16)),
	mmec								MMEC
}

-- ASN1STOP

SCGFailureInformation-r12 ::=		SEQUENCE {
	criticalExtensions					CHOICE {
		c1									CHOICE {
			scgFailureInformation-r12			SCGFailureInformation-r12-IEs,
			spare3 NULL, spare2 NULL, spare1 NULL
		},
		criticalExtensionsFuture			SEQUENCE {}
	}
}

SCGFailureInformation-r12-IEs ::=	SEQUENCE {
	failureReportSCG-r12				FailureReportSCG-r12 			OPTIONAL,
	nonCriticalExtension				SEQUENCE {}							OPTIONAL
}

FailureReportSCG-r12 ::= 			SEQUENCE {
	failureType-r12						ENUMERATED {t313-Expiry, randomAccessProblem,
												rlc-MaxNumRetx, scg-ChangeFailure },
	measResultServFreqList-r12			MeasResultServFreqList-r10		OPTIONAL,
	measResultNeighCells-r12			MeasResultList2EUTRA-r9			OPTIONAL,
--	...,
--	[[
	measResultServFreqListExt-r13			MeasResultServFreqListExt-r13		OPTIONAL
--	]]
}

-- ASN1STOP

SCPTMConfiguration-r13 ::=		SEQUENCE {
	sc-mtch-InfoList-r13			SC-MTCH-InfoList-r13,
	scptmNeighbourCellList-r13		SCPTMNeighbourCellList-r13			OPTIONAL,
	...
}

-- ASN1STOP

SecurityModeCommand ::=				SEQUENCE {
	rrc-TransactionIdentifier			RRC-TransactionIdentifier,
	criticalExtensions					CHOICE {
		c1									CHOICE{
			securityModeCommand-r8				SecurityModeCommand-r8-IEs,
			spare3 NULL, spare2 NULL, spare1 NULL
		},
		criticalExtensionsFuture			SEQUENCE {}
	}
}

SecurityModeCommand-r8-IEs ::=		SEQUENCE {
	securityConfigSMC					SecurityConfigSMC,
	nonCriticalExtension				SecurityModeCommand-v8a0-IEs		OPTIONAL
}

SecurityModeCommand-v8a0-IEs ::= SEQUENCE {
	lateNonCriticalExtension			OCTET STRING						OPTIONAL,
	nonCriticalExtension				SEQUENCE {}							OPTIONAL
}

SecurityConfigSMC ::=					SEQUENCE {
	securityAlgorithmConfig					SecurityAlgorithmConfig,
	...
}

-- ASN1STOP

SecurityModeComplete ::=			SEQUENCE {
	rrc-TransactionIdentifier			RRC-TransactionIdentifier,
	criticalExtensions					CHOICE {
		securityModeComplete-r8				SecurityModeComplete-r8-IEs,
		criticalExtensionsFuture			SEQUENCE {}
	}
}

SecurityModeComplete-r8-IEs ::=		SEQUENCE {
	nonCriticalExtension				SecurityModeComplete-v8a0-IEs							OPTIONAL
}

SecurityModeComplete-v8a0-IEs ::= SEQUENCE {
	lateNonCriticalExtension			OCTET STRING						OPTIONAL,
	nonCriticalExtension				SEQUENCE {}							OPTIONAL
}

-- ASN1STOP

SecurityModeFailure ::=				SEQUENCE {
	rrc-TransactionIdentifier			RRC-TransactionIdentifier,
	criticalExtensions					CHOICE {
		securityModeFailure-r8				SecurityModeFailure-r8-IEs,
		criticalExtensionsFuture			SEQUENCE {}
	}
}

SecurityModeFailure-r8-IEs ::=		SEQUENCE {
	nonCriticalExtension				SecurityModeFailure-v8a0-IEs							OPTIONAL
}

SecurityModeFailure-v8a0-IEs ::= SEQUENCE {
	lateNonCriticalExtension			OCTET STRING						OPTIONAL,
	nonCriticalExtension				SEQUENCE {}							OPTIONAL
}

-- ASN1STOP

SidelinkUEInformation-r12 ::=		SEQUENCE {
	criticalExtensions				CHOICE {
		c1								CHOICE {
			sidelinkUEInformation-r12		SidelinkUEInformation-r12-IEs,
			spare3 NULL, spare2 NULL, spare1 NULL
		},
		criticalExtensionsFuture			SEQUENCE {}
	}
}

SidelinkUEInformation-r12-IEs ::=	SEQUENCE {
	commRxInterestedFreq-r12		ARFCN-ValueEUTRA-r9			OPTIONAL,
	commTxResourceReq-r12			SL-CommTxResourceReq-r12	OPTIONAL,
	discRxInterest-r12				ENUMERATED {true}			OPTIONAL,
	discTxResourceReq-r12			INTEGER (1..63)				OPTIONAL,
	lateNonCriticalExtension		OCTET STRING				OPTIONAL,
	nonCriticalExtension			SidelinkUEInformation-v13x0-IEs	OPTIONAL
}

SidelinkUEInformation-v13x0-IEs ::=	SEQUENCE {
	commTxResourceReq121-r13		SL-CommTxResourceReqUC-r13	OPTIONAL,
	commTxResourceInfoReqRelay-r13		SEQUENCE {
		commTxResourceReqRelay-r13		SL-CommTxResourceReqUC-r13,
		ue-Type-r13						ENUMERATED {relayUE, remoteUE}
	}															OPTIONAL,
	discTxResourceReq-v13x0			SEQUENCE {
		carrierFreqDiscTx-r13			INTEGER (1..maxFreq),
		discTxResourceReqAddFreq-r13	SL-DiscTxResourceReqPerFreqList-r13	OPTIONAL
	}															OPTIONAL,
	discTxResourceReqPS-r13			SL-DiscTxResourceReq-r13	OPTIONAL,
	discRxGapReq-r13					SL-GapRequest-r13			OPTIONAL,
	discTxGapReq-r13					SL-GapRequest-r13			OPTIONAL,
	discSysInfoReportList-r13			SL-SysInfoReportList-r13	OPTIONAL,
	nonCriticalExtension			SEQUENCE {}					OPTIONAL
}

SL-CommTxResourceReq-r12 ::=		SEQUENCE {
	carrierFreq-r12					ARFCN-ValueEUTRA-r9			OPTIONAL,
	destinationInfoList-r12			SL-DestinationInfoList-r12
}

SL-CommTxResourceReqUC-r13 ::=		SEQUENCE {
	carrierFreq-r13					ARFCN-ValueEUTRA-r9			OPTIONAL,
	destinationInfoListUC-r13			SL-DestinationInfoListUC-r13
}

SL-DiscTxResourceReqPerFreqList-r13 ::=	SEQUENCE (SIZE (1..maxFreq)) OF SL-DiscTxResourceReq-r13

SL-DiscTxResourceReq-r13 ::=		SEQUENCE {
	carrierFreq-r13					ARFCN-ValueEUTRA-r9			OPTIONAL,
	discTxResourceReq-r13			INTEGER (1..63)
}

SL-DestinationInfoList-r12 ::=	SEQUENCE (SIZE (1..maxSL-Dest-r12)) OF SL-DestinationIdentity-r12

SL-DestinationIdentity-r12 ::=	BIT STRING (SIZE (24))

SL-DestinationInfoListUC-r13 ::=	SL-DestinationInfoList-r12

SL-SysInfoReportList-r13 ::=	SEQUENCE (SIZE (1.. maxSL-DiscSysInfoReportFreq-r13)) OF SL-SysInfoReport-r13

-- ASN1STOP

SystemInformation ::=				SEQUENCE {
	criticalExtensions					CHOICE {
		systemInformation-r8				SystemInformation-r8-IEs,
		criticalExtensionsFuture			SEQUENCE {}
	}
}
SystemInformation-r8-IEs ::=		SEQUENCE {
	sib-TypeAndInfo						SEQUENCE (SIZE (1..maxSIB)) OF CHOICE {
		sib2								SystemInformationBlockType2,
		sib3								SystemInformationBlockType3,
		sib4								SystemInformationBlockType4,
		sib5								SystemInformationBlockType5,
		sib6								SystemInformationBlockType6,
		sib7								SystemInformationBlockType7,
		sib8								SystemInformationBlockType8,
		sib9								SystemInformationBlockType9,
		sib10								SystemInformationBlockType10,
		sib11								SystemInformationBlockType11,
	--	...,
		sib12-v920							SystemInformationBlockType12-r9,
		sib13-v920							SystemInformationBlockType13-r9,
		sib14-v1130							SystemInformationBlockType14-r11,
		sib15-v1130							SystemInformationBlockType15-r11,
		sib16-v1130							SystemInformationBlockType16-r11,
		sib17-v1250							SystemInformationBlockType17-r12,
		sib18-v1250							SystemInformationBlockType18-r12,
		sib19-v1250							SystemInformationBlockType19-r12,
		sib20-v13x0							SystemInformationBlockType20-r13
	},
	nonCriticalExtension				SystemInformation-v8a0-IEs			OPTIONAL
}

SystemInformation-v8a0-IEs ::= SEQUENCE {
	lateNonCriticalExtension			OCTET STRING						OPTIONAL,
	nonCriticalExtension				SEQUENCE {}							OPTIONAL
}

-- ASN1STOP

SystemInformationBlockType1 ::=		SEQUENCE {
	cellAccessRelatedInfo				SEQUENCE {
		plmn-IdentityList					PLMN-IdentityList,
		trackingAreaCode					TrackingAreaCode,
		cellIdentity						CellIdentity,
		cellBarred							ENUMERATED {barred, notBarred},
		intraFreqReselection				ENUMERATED {allowed, notAllowed},
		csg-Indication						BOOLEAN,
		csg-Identity						CSG-Identity			OPTIONAL	-- Need OR
	},
	cellSelectionInfo					SEQUENCE {
		q-RxLevMin							Q-RxLevMin,
		q-RxLevMinOffset					INTEGER (1..8)			OPTIONAL	-- Need OP
	},
	p-Max								P-Max						OPTIONAL,			-- Need OP
	freqBandIndicator					FreqBandIndicator,
	schedulingInfoList					SchedulingInfoList,
	tdd-Config							TDD-Config					OPTIONAL,	-- Cond TDD
	si-WindowLength						ENUMERATED {
											ms1, ms2, ms5, ms10, ms15, ms20,
											ms40},
	systemInfoValueTag					INTEGER (0..31),
	nonCriticalExtension				SystemInformationBlockType1-v890-IEs	OPTIONAL
}

SystemInformationBlockType1-v890-IEs::=	SEQUENCE {
	lateNonCriticalExtension			OCTET STRING (CONTAINING SystemInformationBlockType1-v8h0-IEs)			OPTIONAL,
	nonCriticalExtension				SystemInformationBlockType1-v920-IEs	OPTIONAL
}

-- Late non critical extensions
SystemInformationBlockType1-v8h0-IEs ::=	SEQUENCE {
	multiBandInfoList					MultiBandInfoList		OPTIONAL,	-- Need OR
	nonCriticalExtension				SystemInformationBlockType1-v9e0-IEs	OPTIONAL
}

SystemInformationBlockType1-v9e0-IEs ::= SEQUENCE {
	freqBandIndicator-v9e0				FreqBandIndicator-v9e0		OPTIONAL,	-- Cond FBI-max
	multiBandInfoList-v9e0				MultiBandInfoList-v9e0		OPTIONAL,	-- Cond mFBI-max
	nonCriticalExtension				SystemInformationBlockType1-v10j0-IEs	OPTIONAL
}

SystemInformationBlockType1-v10j0-IEs ::= SEQUENCE {
	freqBandInfo-r10					NS-PmaxList-r10				OPTIONAL,	-- Need OR
	multiBandInfoList-v10j0				MultiBandInfoList-v10j0		OPTIONAL,	-- Need OR
	nonCriticalExtension				SEQUENCE {}					OPTIONAL
}

-- Regular non critical extensions
SystemInformationBlockType1-v920-IEs ::=	SEQUENCE {
	ims-EmergencySupport-r9				ENUMERATED {true}			OPTIONAL,	-- Need OR
	cellSelectionInfo-v920				CellSelectionInfo-v920		OPTIONAL,	-- Cond RSRQ
	nonCriticalExtension				SystemInformationBlockType1-v1130-IEs	OPTIONAL
}

SystemInformationBlockType1-v1130-IEs ::=	SEQUENCE {
	tdd-Config-v1130				TDD-Config-v1130			OPTIONAL,	-- Cond TDD-OR
	cellSelectionInfo-v1130			CellSelectionInfo-v1130		OPTIONAL,	-- Cond WB-RSRQ
	nonCriticalExtension			SystemInformationBlockType1-v1250-IEs	OPTIONAL
}

SystemInformationBlockType1-v1250-IEs ::=	SEQUENCE {
	cellAccessRelatedInfo-v1250					SEQUENCE {
		category0Allowed-r12						ENUMERATED {true}		OPTIONAL	-- Need OP
	},
	cellSelectionInfo-v1250					CellSelectionInfo-v1250		OPTIONAL,	-- Cond RSRQ2
	freqBandIndicatorPriority-r12			ENUMERATED {true}			OPTIONAL,	-- Cond mFBI
	nonCriticalExtension			SystemInformationBlockType1-v13xy-IEs	OPTIONAL				
}

SystemInformationBlockType1-v13xy-IEs ::=	SEQUENCE {
	hyperSFN						BIT STRING (SIZE (10))		OPTIONAL,
	eDRXAllowed			ENUMERATED {true}		OPTIONAL, 
	nonCriticalExtension			SEQUENCE {}					OPTIONAL
}

PLMN-IdentityList ::=					SEQUENCE (SIZE (1..maxPLMN-r11)) OF PLMN-IdentityInfo

PLMN-IdentityInfo ::=					SEQUENCE {
	plmn-Identity							PLMN-Identity,
	cellReservedForOperatorUse				ENUMERATED {reserved, notReserved}
}

SchedulingInfoList ::= SEQUENCE (SIZE (1..maxSI-Message)) OF SchedulingInfo

SchedulingInfo ::=	SEQUENCE {
	si-Periodicity						ENUMERATED {
											rf8, rf16, rf32, rf64, rf128, rf256, rf512},
	sib-MappingInfo						SIB-MappingInfo
}

SIB-MappingInfo ::= SEQUENCE (SIZE (0..maxSIB-1)) OF SIB-Type

SIB-Type ::=						ENUMERATED {
										sibType3, sibType4, sibType5, sibType6,
										sibType7, sibType8, sibType9, sibType10,
										sibType11, sibType12-v920, sibType13-v920,
										sibType14-v1130, sibType15-v1130,
										sibType16-v1130, sibType17-v1250, sibType18-v1250,
										..., sibType19-v1250, sibType20-v13xy }

CellSelectionInfo-v920 ::=			SEQUENCE {
	q-QualMin-r9						Q-QualMin-r9,
	q-QualMinOffset-r9					INTEGER (1..8)						OPTIONAL	-- Need OP
}

CellSelectionInfo-v1130 ::=			SEQUENCE {
	q-QualMinWB-r11						Q-QualMin-r9
}

CellSelectionInfo-v1250 ::=			SEQUENCE {
	q-QualMinRSRQ-OnAllSymbols-r12						Q-QualMin-r9
}

-- ASN1STOP

UEAssistanceInformation-r11 ::=				SEQUENCE {
	criticalExtensions					CHOICE {
		c1									CHOICE {
			ueAssistanceInformation-r11			UEAssistanceInformation-r11-IEs,
			spare3 NULL, spare2 NULL, spare1 NULL
		},
		criticalExtensionsFuture			SEQUENCE {}
	}
}

UEAssistanceInformation-r11-IEs ::=		SEQUENCE {
	powerPrefIndication-r11				ENUMERATED	{normal, lowPowerConsumption}	OPTIONAL,
	lateNonCriticalExtension			OCTET STRING						OPTIONAL,
	nonCriticalExtension				SEQUENCE {}							OPTIONAL
}

-- ASN1STOP

UECapabilityEnquiry ::=				SEQUENCE {
	rrc-TransactionIdentifier			RRC-TransactionIdentifier,
	criticalExtensions					CHOICE {
		c1									CHOICE {
			ueCapabilityEnquiry-r8				UECapabilityEnquiry-r8-IEs,
			spare3 NULL, spare2 NULL, spare1 NULL
		},
		criticalExtensionsFuture			SEQUENCE {}
	}
}

UECapabilityEnquiry-r8-IEs ::=		SEQUENCE {
	ue-CapabilityRequest				UE-CapabilityRequest,
	nonCriticalExtension				UECapabilityEnquiry-v8a0-IEs		OPTIONAL
}

UECapabilityEnquiry-v8a0-IEs ::= SEQUENCE {
	lateNonCriticalExtension			OCTET STRING						OPTIONAL,
	nonCriticalExtension				UECapabilityEnquiry-v1180-IEs							OPTIONAL
}

UECapabilityEnquiry-v1180-IEs ::= SEQUENCE {
	requestedFrequencyBands-r11			SEQUENCE (SIZE (1..16)) OF FreqBandIndicator-r11							OPTIONAL,
	nonCriticalExtension				UECapabilityEnquiry-v13xy-IEs 							OPTIONAL
}

UECapabilityEnquiry-v13xy-IEs ::= SEQUENCE {
	requestReducedFormat-r13			ENUMERATED {true}					OPTIONAL,
	skipFallbackCombinations-r13		ENUMERATED {true}					OPTIONAL,
	requestedMaxCCsDL-r13			INTEGER (2..32)						OPTIONAL,
	requestedMaxCCsUL-r13			INTEGER (2..32)						OPTIONAL,
	nonCriticalExtension				SEQUENCE {}							OPTIONAL
}

UE-CapabilityRequest ::=		SEQUENCE (SIZE (1..maxRAT-Capabilities)) OF RAT-Type

-- ASN1STOP

UECapabilityInformation ::=			SEQUENCE {
	rrc-TransactionIdentifier			RRC-TransactionIdentifier,
	criticalExtensions					CHOICE {
		c1									CHOICE{
			ueCapabilityInformation-r8			UECapabilityInformation-r8-IEs,
			spare7 NULL,
			spare6 NULL, spare5 NULL, spare4 NULL,
			spare3 NULL, spare2 NULL, spare1 NULL
		},
		criticalExtensionsFuture			SEQUENCE {}
	}
}

UECapabilityInformation-r8-IEs ::=	SEQUENCE {
	ue-CapabilityRAT-ContainerList		UE-CapabilityRAT-ContainerList,
	nonCriticalExtension				UECapabilityInformation-v8a0-IEs	OPTIONAL
}

UECapabilityInformation-v8a0-IEs ::= SEQUENCE {
	lateNonCriticalExtension			OCTET STRING						OPTIONAL,
	nonCriticalExtension				UECapabilityInformation-v1250-IEs	OPTIONAL
}

UECapabilityInformation-v1250-IEs ::= SEQUENCE {
	ue-RadioPagingInfo-r12				UE-RadioPagingInfo-r12				OPTIONAL,
	nonCriticalExtension				SEQUENCE {}							OPTIONAL
}

-- ASN1STOP

UEInformationRequest-r9		::=				SEQUENCE {
	rrc-TransactionIdentifier		RRC-TransactionIdentifier,
	criticalExtensions				CHOICE {
		c1								CHOICE {
			ueInformationRequest-r9				UEInformationRequest-r9-IEs,
			spare3 NULL, spare2 NULL, spare1 NULL
		},
		criticalExtensionsFuture			SEQUENCE {}
	}
}

UEInformationRequest-r9-IEs ::=		SEQUENCE {
	rach-ReportReq-r9					BOOLEAN,
	rlf-ReportReq-r9					BOOLEAN,
	nonCriticalExtension				UEInformationRequest-v930-IEs		OPTIONAL
}

UEInformationRequest-v930-IEs ::= SEQUENCE {
	lateNonCriticalExtension			OCTET STRING						OPTIONAL,
	nonCriticalExtension				UEInformationRequest-v1020-IEs		OPTIONAL
}

UEInformationRequest-v1020-IEs ::=	SEQUENCE {
	logMeasReportReq-r10				ENUMERATED {true}					OPTIONAL,	-- Need ON
	nonCriticalExtension				UEInformationRequest-v1130-IEs		OPTIONAL
}

UEInformationRequest-v1130-IEs ::= SEQUENCE {
	connEstFailReportReq-r11			ENUMERATED {true}					OPTIONAL,	-- Need ON
	nonCriticalExtension				UEInformationRequest-v1250-IEs		OPTIONAL
}

UEInformationRequest-v1250-IEs ::= SEQUENCE {
	mobilityHistoryReportReq-r12		ENUMERATED {true}					OPTIONAL,	-- Need ON
	nonCriticalExtension				SEQUENCE {}							OPTIONAL
}

-- ASN1STOP

UEInformationResponse-r9	::=			SEQUENCE {
	rrc-TransactionIdentifier			RRC-TransactionIdentifier,
	criticalExtensions					CHOICE {
		c1								CHOICE {
			ueInformationResponse-r9				UEInformationResponse-r9-IEs,
			spare3 NULL, spare2 NULL, spare1 NULL
		},
		criticalExtensionsFuture				SEQUENCE {}
	}
}

UEInformationResponse-r9-IEs ::=		SEQUENCE {
	rach-Report-r9							SEQUENCE {
		numberOfPreamblesSent-r9				NumberOfPreamblesSent-r11,
		contentionDetected-r9					BOOLEAN
	}																OPTIONAL,
	rlf-Report-r9							RLF-Report-r9			OPTIONAL,
	nonCriticalExtension					UEInformationResponse-v930-IEs				OPTIONAL
}

-- Late non critical extensions
UEInformationResponse-v9e0-IEs ::= SEQUENCE {
	rlf-Report-v9e0						RLF-Report-v9e0					OPTIONAL,
	nonCriticalExtension				SEQUENCE {}						OPTIONAL
}

-- Regular non critical extensions
UEInformationResponse-v930-IEs ::=	SEQUENCE {
	lateNonCriticalExtension			OCTET STRING (CONTAINING UEInformationResponse-v9e0-IEs)	OPTIONAL,
	nonCriticalExtension				UEInformationResponse-v1020-IEs		OPTIONAL
}

UEInformationResponse-v1020-IEs ::= SEQUENCE {
	logMeasReport-r10					LogMeasReport-r10				OPTIONAL,
	nonCriticalExtension				UEInformationResponse-v1130-IEs		OPTIONAL
}

UEInformationResponse-v1130-IEs ::= SEQUENCE {
	connEstFailReport-r11				ConnEstFailReport-r11			OPTIONAL,
	nonCriticalExtension				UEInformationResponse-v1250-IEs	OPTIONAL
}

UEInformationResponse-v1250-IEs ::= SEQUENCE {
	mobilityHistoryReport-r12			MobilityHistoryReport-r12		OPTIONAL,
	nonCriticalExtension				SEQUENCE {}						OPTIONAL
}

RLF-Report-r9 ::= 					SEQUENCE {
	measResultLastServCell-r9				SEQUENCE {
		rsrpResult-r9							RSRP-Range,
		rsrqResult-r9							RSRQ-Range			OPTIONAL
	},
	measResultNeighCells-r9				SEQUENCE {
		measResultListEUTRA-r9				MeasResultList2EUTRA-r9			OPTIONAL,
		measResultListUTRA-r9				MeasResultList2UTRA-r9			OPTIONAL,
		measResultListGERAN-r9				MeasResultListGERAN				OPTIONAL,
		measResultsCDMA2000-r9				MeasResultList2CDMA2000-r9		OPTIONAL
	}	OPTIONAL,
	...,
--	[[	
	locationInfo-r10				LocationInfo-r10		OPTIONAL,
		failedPCellId-r10						CHOICE {
			cellGlobalId-r10						CellGlobalIdEUTRA,
			pci-arfcn-r10							SEQUENCE {
				physCellId-r10							PhysCellId,
				carrierFreq-r10							ARFCN-ValueEUTRA
			}
		}																OPTIONAL,
		reestablishmentCellId-r10		CellGlobalIdEUTRA				OPTIONAL,
		timeConnFailure-r10				INTEGER (0..1023)				OPTIONAL,
		connectionFailureType-r10		ENUMERATED {rlf, hof}			OPTIONAL,
		previousPCellId-r10				CellGlobalIdEUTRA				OPTIONAL
--	]]
	,
--	[[	
                failedPCellId-v1090				SEQUENCE {
			carrierFreq-v1090				ARFCN-ValueEUTRA-v9e0
		}																OPTIONAL
--	]],
        ,
--	[[
            basicFields-r11					SEQUENCE {
			c-RNTI-r11						C-RNTI,
			rlf-Cause-r11					ENUMERATED {
												t310-Expiry, randomAccessProblem,
												rlc-MaxNumRetx, t312-Expiry-r12},
			timeSinceFailure-r11			TimeSinceFailure-r11
		}																OPTIONAL,
		previousUTRA-CellId-r11			SEQUENCE {
			carrierFreq-r11					ARFCN-ValueUTRA,
			physCellId-r11					CHOICE {
				fdd-r11							PhysCellIdUTRA-FDD,
				tdd-r11							PhysCellIdUTRA-TDD
			},
			cellGlobalId-r11				CellGlobalIdUTRA			OPTIONAL
		}																OPTIONAL,
		selectedUTRA-CellId-r11			SEQUENCE {
			carrierFreq-r11					ARFCN-ValueUTRA,
			physCellId-r11					CHOICE {
				fdd-r11							PhysCellIdUTRA-FDD,
				tdd-r11							PhysCellIdUTRA-TDD
			}
		}																OPTIONAL
--	]]
,
--	[[\n	
                failedPCellId-v1250				SEQUENCE {
			tac-FailedPCell-r12			TrackingAreaCode				
		}																OPTIONAL,
		measResultLastServCell-v1250	RSRQ-Range-v1250				OPTIONAL,
		lastServCellRSRQ-Type-r12		RSRQ-Type-r12					OPTIONAL,
		measResultListEUTRA-v1250		MeasResultList2EUTRA-v1250		OPTIONAL
--	]]
,
--	[[
	droppedQCI-r13					ENUMERATED {qci1}				OPTIONAL
--	]]
}

RLF-Report-v9e0 ::= 				SEQUENCE {
	measResultListEUTRA-v9e0			MeasResultList2EUTRA-v9e0
}

MeasResultList2EUTRA-r9 ::=				SEQUENCE (SIZE (1..maxFreq)) OF MeasResult2EUTRA-r9

MeasResultList2EUTRA-v9e0 ::=			SEQUENCE (SIZE (1..maxFreq)) OF MeasResult2EUTRA-v9e0

MeasResultList2EUTRA-v1250 ::=			SEQUENCE (SIZE (1..maxFreq)) OF MeasResult2EUTRA-v1250

MeasResult2EUTRA-r9 ::=				SEQUENCE {
	carrierFreq-r9						ARFCN-ValueEUTRA,
	measResultList-r9					MeasResultListEUTRA
}

MeasResult2EUTRA-v9e0 ::=				SEQUENCE {
	carrierFreq-v9e0						ARFCN-ValueEUTRA-v9e0		OPTIONAL
}

MeasResult2EUTRA-v1250 ::=				SEQUENCE {
	rsrq-Type-r12							RSRQ-Type-r12		OPTIONAL
}

MeasResultList2UTRA-r9 ::=			SEQUENCE (SIZE (1..maxFreq)) OF MeasResult2UTRA-r9

MeasResult2UTRA-r9 ::=				SEQUENCE {
	carrierFreq-r9						ARFCN-ValueUTRA,
	measResultList-r9					MeasResultListUTRA
}

MeasResultList2CDMA2000-r9 ::=		SEQUENCE (SIZE (1..maxFreq)) OF MeasResult2CDMA2000-r9

MeasResult2CDMA2000-r9 ::= 			SEQUENCE {
	carrierFreq-r9						CarrierFreqCDMA2000,
	measResultList-r9					MeasResultsCDMA2000
}

LogMeasReport-r10 ::= 				SEQUENCE {
	absoluteTimeStamp-r10				AbsoluteTimeInfo-r10,
	traceReference-r10					TraceReference-r10,
	traceRecordingSessionRef-r10		OCTET STRING (SIZE (2)),
	tce-Id-r10							OCTET STRING (SIZE (1)),
	logMeasInfoList-r10					LogMeasInfoList-r10,
	logMeasAvailable-r10				ENUMERATED {true}				OPTIONAL,
	...
}

LogMeasInfoList-r10 ::= 		SEQUENCE (SIZE (1..maxLogMeasReport-r10)) OF LogMeasInfo-r10

LogMeasInfo-r10 ::= 		SEQUENCE {
	locationInfo-r10					LocationInfo-r10		OPTIONAL,
	relativeTimeStamp-r10				INTEGER (0..7200),
	servCellIdentity-r10				CellGlobalIdEUTRA,
	measResultServCell-r10				SEQUENCE {
		rsrpResult-r10						RSRP-Range,
		rsrqResult-r10						RSRQ-Range
	},
	measResultNeighCells-r10			SEQUENCE {
		measResultListEUTRA-r10				MeasResultList2EUTRA-r9		OPTIONAL,
		measResultListUTRA-r10				MeasResultList2UTRA-r9		OPTIONAL,
		measResultListGERAN-r10				MeasResultList2GERAN-r10	OPTIONAL,
		measResultListCDMA2000-r10			MeasResultList2CDMA2000-r9	OPTIONAL
	}	OPTIONAL,
--	...,
	[[	measResultListEUTRA-v1090			MeasResultList2EUTRA-v9e0	OPTIONAL
	]],
	[[	measResultListMBSFN-r12				MeasResultListMBSFN-r12	OPTIONAL,
		measResultServCell-v1250			RSRQ-Range-v1250			OPTIONAL,
		servCellRSRQ-Type-r12				RSRQ-Type-r12				OPTIONAL,
		measResultListEUTRA-v1250			MeasResultList2EUTRA-v1250	OPTIONAL
	]],
	[[	inDeviceCoexDetected-r13			ENUMERATED {true}			OPTIONAL
	]]
}

MeasResultListMBSFN-r12 ::= 			SEQUENCE (SIZE (1..maxMBSFN-Area)) OF MeasResultMBSFN-r12

MeasResultMBSFN-r12 ::= 			SEQUENCE {
	mbsfn-Area-r12							SEQUENCE {
		mbsfn-AreaId-r12						MBSFN-AreaId-r12,
		carrierFreq-r12							ARFCN-ValueEUTRA-r9
	},
	rsrpResultMBSFN-r12						RSRP-Range,
	rsrqResultMBSFN-r12						MBSFN-RSRQ-Range-r12,
	signallingBLER-Result-r12				BLER-Result-r12				OPTIONAL,
	dataBLER-MCH-ResultList-r12				DataBLER-MCH-ResultList-r12	OPTIONAL,
	...
}

DataBLER-MCH-ResultList-r12 ::=			SEQUENCE (SIZE (1.. maxPMCH-PerMBSFN)) OF DataBLER-MCH-Result-r12

DataBLER-MCH-Result-r12 ::= 			SEQUENCE {
	mch-Index-r12							INTEGER (1..maxPMCH-PerMBSFN),
	dataBLER-Result-r12						BLER-Result-r12
}

BLER-Result-r12 ::=					SEQUENCE {
	bler-r12									BLER-Range-r12,
	blocksReceived-r12						SEQUENCE {
		n-r12									BIT STRING (SIZE (3)),		
		m-r12									BIT STRING (SIZE (8))
	}
}

BLER-Range-r12 ::=						INTEGER(0..31)

MeasResultList2GERAN-r10 ::=			SEQUENCE (SIZE (1..maxCellListGERAN)) OF MeasResultListGERAN

ConnEstFailReport-r11 ::= 				SEQUENCE {
	failedCellId-r11					CellGlobalIdEUTRA,
	locationInfo-r11					LocationInfo-r10				OPTIONAL,
	measResultFailedCell-r11				SEQUENCE {
		rsrpResult-r11							RSRP-Range,
		rsrqResult-r11							RSRQ-Range				OPTIONAL
	},
	measResultNeighCells-r11				SEQUENCE {
		measResultListEUTRA-r11				MeasResultList2EUTRA-r9			OPTIONAL,
		measResultListUTRA-r11				MeasResultList2UTRA-r9			OPTIONAL,
		measResultListGERAN-r11				MeasResultListGERAN				OPTIONAL,
		measResultsCDMA2000-r11				MeasResultList2CDMA2000-r9		OPTIONAL
	}	OPTIONAL,
	numberOfPreamblesSent-r11			NumberOfPreamblesSent-r11,
	contentionDetected-r11				BOOLEAN,
	maxTxPowerReached-r11				BOOLEAN,
	timeSinceFailure-r11				TimeSinceFailure-r11,
	measResultListEUTRA-v1130			MeasResultList2EUTRA-v9e0		OPTIONAL,
--	...,
	[[	measResultFailedCell-v1250		RSRQ-Range-v1250				OPTIONAL,
		failedCellRSRQ-Type-r12			RSRQ-Type-r12					OPTIONAL,
		measResultListEUTRA-v1250		MeasResultList2EUTRA-v1250		OPTIONAL
	]]
}

NumberOfPreamblesSent-r11::=			INTEGER (1..200)

TimeSinceFailure-r11 ::=				INTEGER (0..172800)

MobilityHistoryReport-r12 ::=	VisitedCellInfoList-r12

-- ASN1STOP

ULHandoverPreparationTransfer ::=	SEQUENCE {
	criticalExtensions					CHOICE {
		c1									CHOICE {
			ulHandoverPreparationTransfer-r8		ULHandoverPreparationTransfer-r8-IEs,
			spare3 NULL, spare2 NULL, spare1 NULL
		},
		criticalExtensionsFuture				SEQUENCE {}
	}
}

ULHandoverPreparationTransfer-r8-IEs ::= SEQUENCE {
	cdma2000-Type						CDMA2000-Type,
	meid								BIT STRING (SIZE (56))	OPTIONAL,
	dedicatedInfo						DedicatedInfoCDMA2000,
	nonCriticalExtension				ULHandoverPreparationTransfer-v8a0-IEs	OPTIONAL
}

ULHandoverPreparationTransfer-v8a0-IEs ::= SEQUENCE {
	lateNonCriticalExtension			OCTET STRING						OPTIONAL,
	nonCriticalExtension				SEQUENCE {}							OPTIONAL
}

-- ASN1STOP

ULInformationTransfer ::=			SEQUENCE {
	criticalExtensions					CHOICE {
		c1									CHOICE {
			ulInformationTransfer-r8			ULInformationTransfer-r8-IEs,
			spare3 NULL, spare2 NULL, spare1 NULL
		},
		criticalExtensionsFuture			SEQUENCE {}
	}
}

ULInformationTransfer-r8-IEs ::=	SEQUENCE {
	dedicatedInfoType			CHOICE {
		dedicatedInfoNAS					DedicatedInfoNAS,
		dedicatedInfoCDMA2000-1XRTT			DedicatedInfoCDMA2000,
		dedicatedInfoCDMA2000-HRPD			DedicatedInfoCDMA2000
	},
	nonCriticalExtension				ULInformationTransfer-v8a0-IEs							OPTIONAL
}

ULInformationTransfer-v8a0-IEs ::= SEQUENCE {
	lateNonCriticalExtension			OCTET STRING						OPTIONAL,
	nonCriticalExtension				SEQUENCE {}							OPTIONAL
}

-- ASN1STOP

SystemInformationBlockType2 ::=		SEQUENCE {
	ac-BarringInfo						SEQUENCE {
		ac-BarringForEmergency				BOOLEAN,
		ac-BarringForMO-Signalling			AC-BarringConfig				OPTIONAL,	-- Need OP
		ac-BarringForMO-Data				AC-BarringConfig				OPTIONAL	-- Need OP
	}																		OPTIONAL,	-- Need OP
	radioResourceConfigCommon			RadioResourceConfigCommonSIB,
	ue-TimersAndConstants				UE-TimersAndConstants,
	freqInfo							SEQUENCE {
		ul-CarrierFreq						ARFCN-ValueEUTRA				OPTIONAL,	-- Need OP
		ul-Bandwidth						ENUMERATED {n6, n15, n25, n50, n75, n100}
																			OPTIONAL,	-- Need OP
		additionalSpectrumEmission			AdditionalSpectrumEmission
	},
	mbsfn-SubframeConfigList			MBSFN-SubframeConfigList			OPTIONAL, 	-- Need OR
	timeAlignmentTimerCommon			TimeAlignmentTimer,
--	...,
	lateNonCriticalExtension		OCTET STRING (CONTAINING SystemInformationBlockType2-v8h0-IEs)						OPTIONAL,
	[[	ssac-BarringForMMTEL-Voice-r9		AC-BarringConfig				OPTIONAL,	-- Need OP
		ssac-BarringForMMTEL-Video-r9		AC-BarringConfig				OPTIONAL	-- Need OP
	]],
	[[	ac-BarringForCSFB-r10				AC-BarringConfig			OPTIONAL	-- Need OP
	]],
	[[	ac-BarringSkipForMMTELVoice-r12		ENUMERATED {true}			OPTIONAL,	 -- Need OP
		ac-BarringSkipForMMTELVideo-r12		ENUMERATED {true}			OPTIONAL,	 -- Need OP
		ac-BarringSkipForSMS-r12			ENUMERATED {true}			OPTIONAL,	 -- Need OP
		ac-BarringPerPLMN-List-r12			AC-BarringPerPLMN-List-r12	OPTIONAL	-- Need OP
	]],
	[[	voiceServiceCauseIndication-r12		ENUMERATED {true}			OPTIONAL	-- Need OP
	]],
	[[	acdc-BarringForCommon-r13			ACDC-BarringForCommon-r13		OPTIONAL,	-- Need OP
		acdc-BarringPerPLMN-List-r13		ACDC-BarringPerPLMN-List-r13	OPTIONAL	-- Need OP
	]]
}

SystemInformationBlockType2-v8h0-IEs ::=	SEQUENCE {
	multiBandInfoList				SEQUENCE (SIZE (1..maxMultiBands)) OF AdditionalSpectrumEmission	OPTIONAL,	-- Need OR
	nonCriticalExtension			SystemInformationBlockType2-v9e0-IEs	OPTIONAL
}

SystemInformationBlockType2-v9e0-IEs ::= SEQUENCE {
	ul-CarrierFreq-v9e0					ARFCN-ValueEUTRA-v9e0		OPTIONAL,	-- Cond ul-FreqMax
	nonCriticalExtension				SEQUENCE {}					OPTIONAL
}

AC-BarringConfig ::=				SEQUENCE {
	ac-BarringFactor					ENUMERATED {
											p00, p05, p10, p15, p20, p25, p30, p40,
											p50, p60, p70, p75, p80, p85, p90, p95},
	ac-BarringTime						ENUMERATED {s4, s8, s16, s32, s64, s128, s256, s512},
	ac-BarringForSpecialAC				BIT STRING (SIZE(5))
}

MBSFN-SubframeConfigList ::= 		SEQUENCE (SIZE (1..maxMBSFN-Allocations)) OF MBSFN-SubframeConfig

AC-BarringPerPLMN-List-r12 ::= 		SEQUENCE (SIZE (1.. maxPLMN-r11)) OF AC-BarringPerPLMN-r12

AC-BarringPerPLMN-r12 ::=			SEQUENCE {
	plmn-IdentityIndex-r12					INTEGER (1..maxPLMN-r11),
	ac-BarringInfo-r12						SEQUENCE {
		ac-BarringForEmergency-r12			BOOLEAN,
		ac-BarringForMO-Signalling-r12		AC-BarringConfig	OPTIONAL,	-- Need OP
		ac-BarringForMO-Data-r12			AC-BarringConfig	OPTIONAL	-- Need OP
	}															OPTIONAL,	-- Need OP
	ac-BarringSkipForMMTELVoice-r12		ENUMERATED {true}		OPTIONAL,	-- Need OP
	ac-BarringSkipForMMTELVideo-r12		ENUMERATED {true}		OPTIONAL,	-- Need OP
	ac-BarringSkipForSMS-r12			ENUMERATED {true}		OPTIONAL,	-- Need OP
	ac-BarringForCSFB-r12				AC-BarringConfig		OPTIONAL,	-- Need OP
	ssac-BarringForMMTEL-Voice-r12		AC-BarringConfig		OPTIONAL,	-- Need OP
	ssac-BarringForMMTEL-Video-r12		AC-BarringConfig		OPTIONAL	-- Need OP
}

ACDC-BarringForCommon-r13 ::=			SEQUENCE {
	acdc-HPLMNonly-r13					BOOLEAN,
	barringPerACDC-CategoryList-r13				BarringPerACDC-CategoryList-r13
}

ACDC-BarringPerPLMN-List-r13 ::= 		SEQUENCE (SIZE (1.. maxPLMN-r11)) OF ACDC-BarringPerPLMN-r13

ACDC-BarringPerPLMN-r13 ::=			SEQUENCE {
	plmn-IdentityIndex-r13				INTEGER (1..maxPLMN-r11),
	acdc-HPLMNonly-r13					BOOLEAN,
	barringPerACDC-CategoryList-r13				BarringPerACDC-CategoryList-r13
}

BarringPerACDC-CategoryList-r13 ::= SEQUENCE (SIZE (1..maxACDC-Cat-r13)) OF BarringPerACDC-Category-r13

BarringPerACDC-Category-r13 ::= SEQUENCE {
	acdc-CatValue-r13				INTEGER (1..maxACDC-Cat-r13),
	acdc-BarringConfig-r13			SEQUENCE {
		ac-BarringFactor-r13			ENUMERATED {
											p00, p05, p10, p15, p20, p25, p30, p40,
											p50, p60, p70, p75, p80, p85, p90, p95},
		ac-BarringTime-r13				ENUMERATED {s4, s8, s16, s32, s64, s128, s256, s512}
	}										OPTIONAL
}

-- ASN1STOP

SystemInformationBlockType3 ::=		SEQUENCE {
	cellReselectionInfoCommon			SEQUENCE {
		q-Hyst								ENUMERATED {
												dB0, dB1, dB2, dB3, dB4, dB5, dB6, dB8, dB10,
												dB12, dB14, dB16, dB18, dB20, dB22, dB24},
		speedStateReselectionPars			SEQUENCE {
			mobilityStateParameters				MobilityStateParameters,
			q-HystSF						SEQUENCE {
				sf-Medium						ENUMERATED {
														dB-6, dB-4, dB-2, dB0},
				sf-High							ENUMERATED {
														dB-6, dB-4, dB-2, dB0}
			}
		}																OPTIONAL		-- Need OP
	},
	cellReselectionServingFreqInfo		SEQUENCE {
		s-NonIntraSearch					ReselectionThreshold		OPTIONAL,		-- Need OP
		threshServingLow					ReselectionThreshold,
		cellReselectionPriority				CellReselectionPriority
	},
	intraFreqCellReselectionInfo		SEQUENCE {
		q-RxLevMin							Q-RxLevMin,
		p-Max								P-Max						OPTIONAL,		-- Need OP
		s-IntraSearch						ReselectionThreshold		OPTIONAL,		-- Need OP
		allowedMeasBandwidth				AllowedMeasBandwidth		OPTIONAL,		-- Need OP
		presenceAntennaPort1				PresenceAntennaPort1,
		neighCellConfig						NeighCellConfig,
		t-ReselectionEUTRA					T-Reselection,
		t-ReselectionEUTRA-SF				SpeedStateScaleFactors		OPTIONAL		-- Need OP
	},
--	...,
	lateNonCriticalExtension				OCTET STRING (CONTAINING SystemInformationBlockType3-v10j0-IEs)	OPTIONAL,
	[[	s-IntraSearch-v920					SEQUENCE {
			s-IntraSearchP-r9					ReselectionThreshold,
			s-IntraSearchQ-r9					ReselectionThresholdQ-r9
		}																OPTIONAL,		-- Need OP
		s-NonIntraSearch-v920				SEQUENCE {
			s-NonIntraSearchP-r9				ReselectionThreshold,
			s-NonIntraSearchQ-r9				ReselectionThresholdQ-r9
		}																OPTIONAL,		-- Need OP
		q-QualMin-r9						Q-QualMin-r9				OPTIONAL,		-- Need OP
		threshServingLowQ-r9				ReselectionThresholdQ-r9	OPTIONAL		-- Need OP
	]],
	[[	q-QualMinWB-r11						Q-QualMin-r9				OPTIONAL	-- Cond WB-RSRQ
	]],
	[[	q-QualMinRSRQ-OnAllSymbols-r12			Q-QualMin-r9				OPTIONAL			-- Cond RSRQ
	]],
	[[	cellReselectionServingFreqInfo-v13xy CellReselectionServingFreqInfo-v13xy 	OPTIONAL,		-- Need OP
		redistributionServingInfo-r13			RedistributionServingInfo-r13 OPTIONAL	--Need OR
	]]
}

RedistributionServingInfo-r13 ::=		SEQUENCE {
	redistributionFactorServing-r13		INTEGER(0..10),
	redistributionFactorCell-r13		ENUMERATED{true}				OPTIONAL,	--Need OP
	t360-r13							ENUMERATED {min4, min8, min16, min32,infinity,
											spare3,spare2,spare1},
	redistrOnPagingOnly-r13				ENUMERATED {true}		OPTIONAL	--Need OP
}

CellReselectionServingFreqInfo-v13xy ::=	SEQUENCE {
	cellReselectionSubPriority-r13				CellReselectionSubPriority-r13
}

-- Late non critical extensions
SystemInformationBlockType3-v10j0-IEs ::= SEQUENCE {
	freqBandInfo-r10					NS-PmaxList-r10				OPTIONAL,	-- Need OR
	multiBandInfoList-v10j0				MultiBandInfoList-v10j0		OPTIONAL,	-- Need OR
	nonCriticalExtension				SEQUENCE {}					OPTIONAL
}

-- ASN1STOP

SystemInformationBlockType4 ::=		SEQUENCE {
	intraFreqNeighCellList				IntraFreqNeighCellList		OPTIONAL,	-- Need OR
	intraFreqBlackCellList				IntraFreqBlackCellList				OPTIONAL,	-- Need OR
	csg-PhysCellIdRange					PhysCellIdRange				OPTIONAL,	-- Cond CSG
--	...,
	lateNonCriticalExtension				OCTET STRING				OPTIONAL
}

IntraFreqNeighCellList ::=		SEQUENCE (SIZE (1..maxCellIntra)) OF IntraFreqNeighCellInfo

IntraFreqNeighCellInfo ::=		SEQUENCE {
	physCellId								PhysCellId,
	q-OffsetCell							Q-OffsetRange,
	...
}

IntraFreqBlackCellList ::=		SEQUENCE (SIZE (1..maxCellBlack)) OF PhysCellIdRange

-- ASN1STOP

SystemInformationBlockType5 ::=		SEQUENCE {
	interFreqCarrierFreqList			InterFreqCarrierFreqList,
--	...,
	lateNonCriticalExtension				OCTET STRING	(CONTAINING SystemInformationBlockType5-v8h0-IEs)				OPTIONAL,
	[[	interFreqCarrierFreqList-v1250	InterFreqCarrierFreqList-v1250		OPTIONAL,	-- Need OR
		interFreqCarrierFreqListExt-r12	InterFreqCarrierFreqListExt-r12 	OPTIONAL	-- Need OR
	]],
	[[	interFreqCarrierFreqListExt-v1280	InterFreqCarrierFreqListExt-v1280 	OPTIONAL	-- Need OR
	]],
	[[	interFreqCarrierFreqList-v13xy		InterFreqCarrierFreqList-v13xy		OPTIONAL,	-- Need OR
		interFreqCarrierFreqListExt-v13xy	InterFreqCarrierFreqListExt-v13xy 	OPTIONAL	-- Need OR
	]]
}

SystemInformationBlockType5-v8h0-IEs ::=	SEQUENCE {
	interFreqCarrierFreqList-v8h0 SEQUENCE (SIZE (1..maxFreq)) OF InterFreqCarrierFreqInfo-v8h0				 OPTIONAL,	-- Need OP
	nonCriticalExtension			SystemInformationBlockType5-v9e0-IEs							OPTIONAL
}

SystemInformationBlockType5-v9e0-IEs ::=	SEQUENCE {
	interFreqCarrierFreqList-v9e0	SEQUENCE (SIZE (1..maxFreq)) OF InterFreqCarrierFreqInfo-v9e0				OPTIONAL,	-- Need OR
	nonCriticalExtension			SystemInformationBlockType5-v10j0-IEs	OPTIONAL
}

SystemInformationBlockType5-v10j0-IEs ::=	SEQUENCE {
	interFreqCarrierFreqList-v10j0	SEQUENCE (SIZE (1..maxFreq)) OF InterFreqCarrierFreqInfo-v10j0				OPTIONAL,	-- Need OR
	nonCriticalExtension			SEQUENCE {}						OPTIONAL
}

InterFreqCarrierFreqList ::=		SEQUENCE (SIZE (1..maxFreq)) OF InterFreqCarrierFreqInfo

InterFreqCarrierFreqList-v1250 ::=	SEQUENCE (SIZE (1.. maxFreq)) OF InterFreqCarrierFreqInfo-v1250

InterFreqCarrierFreqListExt-r12 ::=	SEQUENCE (SIZE (1.. maxFreq)) OF InterFreqCarrierFreqInfo-r12

InterFreqCarrierFreqListExt-v1280 ::=	SEQUENCE (SIZE (1.. maxFreq)) OF InterFreqCarrierFreqInfo-v10j0

InterFreqCarrierFreqList-v13xy ::=	SEQUENCE (SIZE (1.. maxFreq)) OF InterFreqCarrierFreqInfo-v13xy

InterFreqCarrierFreqListExt-v13xy ::=	SEQUENCE (SIZE (1.. maxFreq)) OF InterFreqCarrierFreqInfo-v13xy

InterFreqCarrierFreqInfo ::=	SEQUENCE {
	dl-CarrierFreq						ARFCN-ValueEUTRA,
	q-RxLevMin							Q-RxLevMin,
	p-Max								P-Max							OPTIONAL,		-- Need OP
	t-ReselectionEUTRA					T-Reselection,
	t-ReselectionEUTRA-SF				SpeedStateScaleFactors			OPTIONAL,		-- Need OP
	threshX-High						ReselectionThreshold,
	threshX-Low							ReselectionThreshold,
	allowedMeasBandwidth				AllowedMeasBandwidth,
	presenceAntennaPort1				PresenceAntennaPort1,
	cellReselectionPriority				CellReselectionPriority			OPTIONAL,		-- Need OP
	neighCellConfig						NeighCellConfig,
	q-OffsetFreq						Q-OffsetRange					DEFAULT dB0,
	interFreqNeighCellList				InterFreqNeighCellList			OPTIONAL, 		-- Need OR
	interFreqBlackCellList				InterFreqBlackCellList			OPTIONAL, 		-- Need OR
--	...,
	[[	q-QualMin-r9					Q-QualMin-r9					OPTIONAL,		-- Need OP
		threshX-Q-r9					SEQUENCE {
			threshX-HighQ-r9				ReselectionThresholdQ-r9,
			threshX-LowQ-r9					ReselectionThresholdQ-r9
		}																OPTIONAL		-- Cond RSRQ
	]],
	[[	q-QualMinWB-r11					Q-QualMin-r9					OPTIONAL	-- Cond WB-RSRQ
	]]
}

InterFreqCarrierFreqInfo-v8h0 ::=		SEQUENCE {
	multiBandInfoList					MultiBandInfoList				OPTIONAL	-- Need OR
}

InterFreqCarrierFreqInfo-v9e0 ::=	SEQUENCE {
	dl-CarrierFreq-v9e0					ARFCN-ValueEUTRA-v9e0	OPTIONAL,	-- Cond dl-FreqMax
	multiBandInfoList-v9e0				MultiBandInfoList-v9e0	OPTIONAL	-- Need OR
}

InterFreqCarrierFreqInfo-v10j0 ::=	SEQUENCE {
	freqBandInfo-r10					NS-PmaxList-r10				OPTIONAL,	-- Need OR
	multiBandInfoList-v10j0				MultiBandInfoList-v10j0		OPTIONAL	-- Need OR
}

InterFreqCarrierFreqInfo-v1250 ::=		SEQUENCE {
	reducedMeasPerformance-r12		ENUMERATED {true}		OPTIONAL,		-- Need OP
	q-QualMinRSRQ-OnAllSymbols-r12	Q-QualMin-r9					OPTIONAL	-- Cond RSRQ2
}

InterFreqCarrierFreqInfo-r12 ::=		SEQUENCE {
	dl-CarrierFreq-r12					ARFCN-ValueEUTRA-r9,
	q-RxLevMin-r12						Q-RxLevMin,
	p-Max-r12							P-Max							OPTIONAL,		-- Need OP
	t-ReselectionEUTRA-r12				T-Reselection,
	t-ReselectionEUTRA-SF-r12			SpeedStateScaleFactors			OPTIONAL,		-- Need OP
	threshX-High-r12					ReselectionThreshold,
	threshX-Low-r12						ReselectionThreshold,
	allowedMeasBandwidth-r12			AllowedMeasBandwidth,
	presenceAntennaPort1-r12			PresenceAntennaPort1,
	cellReselectionPriority-r12			CellReselectionPriority			OPTIONAL,		-- Need OP
	neighCellConfig-r12					NeighCellConfig,
	q-OffsetFreq-r12					Q-OffsetRange					DEFAULT dB0,
	interFreqNeighCellList-r12			InterFreqNeighCellList			OPTIONAL, 		-- Need OR
	interFreqBlackCellList-r12			InterFreqBlackCellList			OPTIONAL, 		-- Need OR
	q-QualMin-r12						Q-QualMin-r9					OPTIONAL,		-- Need OP
	threshX-Q-r12						SEQUENCE {
		threshX-HighQ-r12					ReselectionThresholdQ-r9,
		threshX-LowQ-r12					ReselectionThresholdQ-r9
	}																	OPTIONAL,	-- Cond RSRQ
	q-QualMinWB-r12						Q-QualMin-r9					OPTIONAL,	-- Cond WB-RSRQ
	multiBandInfoList-r12				MultiBandInfoList-r11			OPTIONAL,	-- Need OR
	reducedMeasPerformance-r12			ENUMERATED {true}				OPTIONAL,	-- Need OP
	q-QualMinRSRQ-OnAllSymbols-r12		Q-QualMin-r9					OPTIONAL,	-- Cond RSRQ2
...
}

InterFreqCarrierFreqInfo-v13xy	::=	SEQUENCE {
	cellReselectionSubPriority-r13		CellReselectionSubPriority-r13		OPTIONAL,		-- Need OP
	redistributionInterFreqInfo-r13		RedistributionInterFreqInfo-r13		OPTIONAL --Need OP
}

InterFreqNeighCellList ::=			SEQUENCE (SIZE (1..maxCellInter)) OF InterFreqNeighCellInfo

InterFreqNeighCellInfo ::=			SEQUENCE {
	physCellId							PhysCellId,
	q-OffsetCell						Q-OffsetRange
}

InterFreqBlackCellList ::=			SEQUENCE (SIZE (1..maxCellBlack)) OF PhysCellIdRange

RedistributionInterFreqInfo-r13 ::=		SEQUENCE {
	redistributionFactorFreq-r13			RedistributionFactor-r13	OPTIONAL,	--Need OP
	redistributionNeighCellList-r13			RedistributionNeighCellList-r13		OPTIONAL	--Need OP
}

RedistributionNeighCellList-r13 ::=		SEQUENCE (SIZE (1..maxCellInter)) OF RedistributionNeighCell-r13

RedistributionNeighCell-r13 ::=		SEQUENCE {
	physCellId										PhysCellId,
	redistributionFactorCell-r13					RedistributionFactor-r13
}

RedistributionFactor-r13 ::=	INTEGER(1..10)

-- ASN1STOP

SystemInformationBlockType6 ::=		SEQUENCE {
	carrierFreqListUTRA-FDD				CarrierFreqListUTRA-FDD			OPTIONAL, 		-- Need OR
	carrierFreqListUTRA-TDD				CarrierFreqListUTRA-TDD			OPTIONAL, 		-- Need OR
	t-ReselectionUTRA					T-Reselection,
	t-ReselectionUTRA-SF				SpeedStateScaleFactors			OPTIONAL,		-- Need OP
--	...,
	lateNonCriticalExtension			OCTET STRING	(CONTAINING SystemInformationBlockType6-v8h0-IEs)					OPTIONAL,
	[[	carrierFreqListUTRA-FDD-v1250 SEQUENCE (SIZE (1..maxUTRA-FDD-Carrier)) OF
										CarrierFreqInfoUTRA-v1250		OPTIONAL,	-- Cond UTRA-FDD
		carrierFreqListUTRA-TDD-v1250 SEQUENCE (SIZE (1..maxUTRA-TDD-Carrier)) OF
										CarrierFreqInfoUTRA-v1250		OPTIONAL,	-- Cond UTRA-TDD
		carrierFreqListUTRA-FDD-Ext-r12	CarrierFreqListUTRA-FDD-Ext-r12 OPTIONAL,	-- Cond UTRA-FDD
		carrierFreqListUTRA-TDD-Ext-r12 	CarrierFreqListUTRA-TDD-Ext-r12 OPTIONAL		-- Cond UTRA-TDD
	]]
}

SystemInformationBlockType6-v8h0-IEs ::=	SEQUENCE {
	carrierFreqListUTRA-FDD-v8h0 SEQUENCE (SIZE (1..maxUTRA-FDD-Carrier)) OF CarrierFreqInfoUTRA-FDD-v8h0 OPTIONAL,	-- Cond UTRA-FDD
	nonCriticalExtension			
SEQUENCE {}							OPTIONAL
}

CarrierFreqInfoUTRA-v1250 ::=		SEQUENCE {
	reducedMeasPerformance-r12		ENUMERATED {true}		OPTIONAL		-- Need OP
}

CarrierFreqListUTRA-FDD ::=		SEQUENCE (SIZE (1..maxUTRA-FDD-Carrier)) OF CarrierFreqUTRA-FDD 

CarrierFreqUTRA-FDD ::=				SEQUENCE {
	carrierFreq							ARFCN-ValueUTRA,
	cellReselectionPriority				CellReselectionPriority			OPTIONAL, 		-- Need OP
	threshX-High						ReselectionThreshold,
	threshX-Low							ReselectionThreshold,
	q-RxLevMin							INTEGER (-60..-13),
	p-MaxUTRA							INTEGER (-50..33),
	q-QualMin							INTEGER (-24..0),
--	...,
	[[	threshX-Q-r9					SEQUENCE {
			threshX-HighQ-r9				ReselectionThresholdQ-r9,
			threshX-LowQ-r9					ReselectionThresholdQ-r9
		}																OPTIONAL		-- Cond RSRQ
	]]
}

CarrierFreqInfoUTRA-FDD-v8h0 ::=			SEQUENCE {
	multiBandInfoList					SEQUENCE (SIZE (1..maxMultiBands)) OF FreqBandIndicator-UTRA-FDD				OPTIONAL	-- Need OR
}

CarrierFreqListUTRA-FDD-Ext-r12 ::=	SEQUENCE (SIZE (1..maxUTRA-FDD-Carrier)) OF
									 CarrierFreqUTRA-FDD-Ext-r12

CarrierFreqUTRA-FDD-Ext-r12 ::= 				SEQUENCE {
	carrierFreq-r12						ARFCN-ValueUTRA,
	cellReselectionPriority-r12			CellReselectionPriority			OPTIONAL, 	-- Need OP
	threshX-High-r12					ReselectionThreshold,
	threshX-Low-r12						ReselectionThreshold,
	q-RxLevMin-r12						INTEGER (-60..-13),
	p-MaxUTRA-r12						INTEGER (-50..33),
	q-QualMin-r12						INTEGER (-24..0),
	threshX-Q-r12						SEQUENCE {
			threshX-HighQ-r12				ReselectionThresholdQ-r9,
			threshX-LowQ-r12				ReselectionThresholdQ-r9
	}																OPTIONAL,		-- Cond RSRQ
	multiBandInfoList-r12				SEQUENCE (SIZE (1..maxMultiBands)) OF FreqBandIndicator-UTRA-FDD				OPTIONAL,	-- Need OR
	reducedMeasPerformance-r12			ENUMERATED {true}				OPTIONAL,	-- Need OP
	...
}

CarrierFreqListUTRA-TDD ::=		SEQUENCE (SIZE (1..maxUTRA-TDD-Carrier)) OF CarrierFreqUTRA-TDD 

CarrierFreqUTRA-TDD ::=				SEQUENCE {
	carrierFreq							ARFCN-ValueUTRA,
	cellReselectionPriority				CellReselectionPriority			OPTIONAL, 		-- Need OP
	threshX-High						ReselectionThreshold,
	threshX-Low							ReselectionThreshold,
	q-RxLevMin							INTEGER (-60..-13),
	p-MaxUTRA							INTEGER (-50..33),
	...
}

CarrierFreqListUTRA-TDD-Ext-r12 ::=	SEQUENCE (SIZE (1..maxUTRA-TDD-Carrier)) OF
									 CarrierFreqUTRA-TDD-r12

CarrierFreqUTRA-TDD-r12 ::=	SEQUENCE {
	carrierFreq-r12						ARFCN-ValueUTRA,
	cellReselectionPriority-r12			CellReselectionPriority			OPTIONAL, 		-- Need OP
	threshX-High-r12					ReselectionThreshold,
	threshX-Low-r12						ReselectionThreshold,
	q-RxLevMin-r12						INTEGER (-60..-13),
	p-MaxUTRA-r12						INTEGER (-50..33),
	reducedMeasPerformance-r12			ENUMERATED {true}				OPTIONAL,	-- Need OP
	...
}

FreqBandIndicator-UTRA-FDD ::=				INTEGER (1..86)

-- ASN1STOP

SystemInformationBlockType7 ::=		SEQUENCE {
	t-ReselectionGERAN					T-Reselection,
	t-ReselectionGERAN-SF				SpeedStateScaleFactors				OPTIONAL,	-- Need OR
	carrierFreqsInfoList				CarrierFreqsInfoListGERAN			OPTIONAL,	-- Need OR
--	...,
	lateNonCriticalExtension				OCTET STRING				OPTIONAL
}

CarrierFreqsInfoListGERAN ::=			SEQUENCE (SIZE (1..maxGNFG)) OF CarrierFreqsInfoGERAN

CarrierFreqsInfoGERAN ::=			SEQUENCE {
	carrierFreqs						CarrierFreqsGERAN,
	commonInfo							SEQUENCE {
		cellReselectionPriority				CellReselectionPriority			OPTIONAL,	-- Need OP
		ncc-Permitted						BIT STRING (SIZE (8)),
		q-RxLevMin							INTEGER (0..45),
		p-MaxGERAN							INTEGER (0..39)					OPTIONAL,	-- Need OP
		threshX-High						ReselectionThreshold,
		threshX-Low							ReselectionThreshold
	},
	...
}

-- ASN1STOP

SystemInformationBlockType8 ::=		SEQUENCE {
	systemTimeInfo						SystemTimeInfoCDMA2000				OPTIONAL,	-- Need OR
	searchWindowSize					INTEGER (0..15)						OPTIONAL,	-- Need OR
	parametersHRPD						SEQUENCE {
		preRegistrationInfoHRPD				PreRegistrationInfoHRPD,
		cellReselectionParametersHRPD		CellReselectionParametersCDMA2000	OPTIONAL -- Need OR
	}																		OPTIONAL,	-- Need OR
	parameters1XRTT						SEQUENCE {
		csfb-RegistrationParam1XRTT			CSFB-RegistrationParam1XRTT		OPTIONAL,	-- Need OP
		longCodeState1XRTT					BIT STRING (SIZE (42))			OPTIONAL,	-- Need OR
		cellReselectionParameters1XRTT		CellReselectionParametersCDMA2000	OPTIONAL -- Need OR
	}																		OPTIONAL,	-- Need OR
--	...,
	lateNonCriticalExtension			OCTET STRING						OPTIONAL,
	[[	csfb-SupportForDualRxUEs-r9			BOOLEAN							OPTIONAL,	-- Need OR
		cellReselectionParametersHRPD-v920	CellReselectionParametersCDMA2000-v920	OPTIONAL,	-- Cond NCL-HRPD
		cellReselectionParameters1XRTT-v920	CellReselectionParametersCDMA2000-v920	OPTIONAL,	-- Cond NCL-1XRTT
		csfb-RegistrationParam1XRTT-v920	CSFB-RegistrationParam1XRTT-v920		OPTIONAL,	-- Cond REG-1XRTT
		ac-BarringConfig1XRTT-r9			AC-BarringConfig1XRTT-r9	OPTIONAL	-- Cond REG-1XRTT
	]],
	[[	csfb-DualRxTxSupport-r10			ENUMERATED {true}			OPTIONAL	-- Cond REG-1XRTT
	]],
	[[	sib8-PerPLMN-List-r11				SIB8-PerPLMN-List-r11		OPTIONAL	-- Need OR
	]]
}

CellReselectionParametersCDMA2000 ::= SEQUENCE {
	bandClassList						BandClassListCDMA2000,
	neighCellList						NeighCellListCDMA2000,
	t-ReselectionCDMA2000			T-Reselection,
	t-ReselectionCDMA2000-SF			SpeedStateScaleFactors				OPTIONAL	-- Need OP
}

CellReselectionParametersCDMA2000-r11 ::= SEQUENCE {
	bandClassList						BandClassListCDMA2000,
	neighCellList-r11					SEQUENCE (SIZE (1..16)) OF NeighCellCDMA2000-r11,
	t-ReselectionCDMA2000				T-Reselection,
	t-ReselectionCDMA2000-SF			SpeedStateScaleFactors				OPTIONAL	-- Need OP
}

CellReselectionParametersCDMA2000-v920 ::= SEQUENCE {
	neighCellList-v920						NeighCellListCDMA2000-v920
}

NeighCellListCDMA2000 ::=			SEQUENCE (SIZE (1..16)) OF NeighCellCDMA2000

NeighCellCDMA2000 ::=	SEQUENCE {
	bandClass							BandclassCDMA2000,
	neighCellsPerFreqList				NeighCellsPerBandclassListCDMA2000
}

NeighCellCDMA2000-r11 ::=	SEQUENCE {
	bandClass							BandclassCDMA2000,
	neighFreqInfoList-r11				SEQUENCE (SIZE (1..16)) OF NeighCellsPerBandclassCDMA2000-r11
}

NeighCellsPerBandclassListCDMA2000 ::= SEQUENCE (SIZE (1..16)) OF NeighCellsPerBandclassCDMA2000

NeighCellsPerBandclassCDMA2000 ::=	SEQUENCE {
	arfcn								ARFCN-ValueCDMA2000,
	physCellIdList						PhysCellIdListCDMA2000
}

NeighCellsPerBandclassCDMA2000-r11 ::=	SEQUENCE {
	arfcn								ARFCN-ValueCDMA2000,
	physCellIdList-r11					SEQUENCE (SIZE (1..40)) OF PhysCellIdCDMA2000
}

NeighCellListCDMA2000-v920 ::=		SEQUENCE (SIZE (1..16)) OF NeighCellCDMA2000-v920

NeighCellCDMA2000-v920 ::=			SEQUENCE {
	neighCellsPerFreqList-v920			NeighCellsPerBandclassListCDMA2000-v920
}

NeighCellsPerBandclassListCDMA2000-v920 ::= SEQUENCE (SIZE (1..16)) OF NeighCellsPerBandclassCDMA2000-v920

NeighCellsPerBandclassCDMA2000-v920 ::=	SEQUENCE {
	physCellIdList-v920					PhysCellIdListCDMA2000-v920
}

PhysCellIdListCDMA2000 ::=			SEQUENCE (SIZE (1..16)) OF PhysCellIdCDMA2000

PhysCellIdListCDMA2000-v920 ::=		SEQUENCE (SIZE (0..24)) OF PhysCellIdCDMA2000

BandClassListCDMA2000 ::=			SEQUENCE (SIZE (1..maxCDMA-BandClass)) OF BandClassInfoCDMA2000

BandClassInfoCDMA2000 ::=	SEQUENCE {
	bandClass							BandclassCDMA2000,
	cellReselectionPriority				CellReselectionPriority				OPTIONAL,	-- Need OP
	threshX-High						INTEGER (0..63),
	threshX-Low							INTEGER (0..63),
	...
}

AC-BarringConfig1XRTT-r9 ::=		SEQUENCE {
	ac-Barring0to9-r9					INTEGER (0..63),
	ac-Barring10-r9						INTEGER (0..7),
	ac-Barring11-r9						INTEGER (0..7),
	ac-Barring12-r9						INTEGER (0..7),
	ac-Barring13-r9						INTEGER (0..7),
	ac-Barring14-r9						INTEGER (0..7),
	ac-Barring15-r9						INTEGER (0..7),
	ac-BarringMsg-r9					INTEGER (0..7),
	ac-BarringReg-r9					INTEGER (0..7),
	ac-BarringEmg-r9					INTEGER (0..7)
}

SIB8-PerPLMN-List-r11 ::=			SEQUENCE (SIZE (1..maxPLMN-r11)) OF SIB8-PerPLMN-r11

SIB8-PerPLMN-r11 ::=				SEQUENCE {
	plmn-Identity-r11					INTEGER (1..maxPLMN-r11),
	parametersCDMA2000-r11				CHOICE {
		explicitValue						ParametersCDMA2000-r11,
		defaultValue						NULL
	}
}

ParametersCDMA2000-r11 ::=			SEQUENCE {
	systemTimeInfo-r11					CHOICE	{
		explicitValue						SystemTimeInfoCDMA2000,
		defaultValue						NULL
	}																OPTIONAL,	-- Need OR
	searchWindowSize-r11				INTEGER (0..15),
	parametersHRPD-r11					SEQUENCE {
		preRegistrationInfoHRPD-r11			PreRegistrationInfoHRPD,
		cellReselectionParametersHRPD-r11	CellReselectionParametersCDMA2000-r11	OPTIONAL -- Need OR
	}		OPTIONAL,	-- Need OR
	parameters1XRTT-r11					SEQUENCE {
		csfb-RegistrationParam1XRTT-r11		CSFB-RegistrationParam1XRTT			OPTIONAL, -- Need OP
		csfb-RegistrationParam1XRTT-Ext-r11	CSFB-RegistrationParam1XRTT-v920	OPTIONAL, -- Cond REG-1XRTT-PerPLMN
		longCodeState1XRTT-r11				BIT STRING (SIZE (42))	OPTIONAL, -- Cond PerPLMN-LC
		cellReselectionParameters1XRTT-r11	CellReselectionParametersCDMA2000-r11	OPTIONAL, -- Need OR
		ac-BarringConfig1XRTT-r11			AC-BarringConfig1XRTT-r9			OPTIONAL, -- Cond REG-1XRTT-PerPLMN
		csfb-SupportForDualRxUEs-r11		BOOLEAN								OPTIONAL, -- Need OR
		csfb-DualRxTxSupport-r11			ENUMERATED {true}			OPTIONAL -- Cond REG-1XRTT-PerPLMN
	}		OPTIONAL,	-- Need OR
	...
}

-- ASN1STOP

SystemInformationBlockType9 ::=		SEQUENCE {
	hnb-Name							OCTET STRING (SIZE(1..48))		OPTIONAL,	-- Need OR
--	...,
	lateNonCriticalExtension				OCTET STRING				OPTIONAL
}

-- ASN1STOP

SystemInformationBlockType10 ::=	SEQUENCE {
	messageIdentifier					BIT STRING (SIZE (16)),
	serialNumber						BIT STRING (SIZE (16)),
	warningType							OCTET STRING (SIZE (2)),
	dummy								OCTET STRING (SIZE (50))	OPTIONAL,		-- Need OP
--	...,
	lateNonCriticalExtension			OCTET STRING				OPTIONAL
}

-- ASN1STOP

SystemInformationBlockType11 ::=	SEQUENCE {
	messageIdentifier					BIT STRING (SIZE (16)),
	serialNumber						BIT STRING (SIZE (16)),
	warningMessageSegmentType			ENUMERATED {notLastSegment, lastSegment},
	warningMessageSegmentNumber			INTEGER (0..63),
	warningMessageSegment				OCTET STRING,
	dataCodingScheme					OCTET STRING (SIZE (1)) 		OPTIONAL, 	-- Cond Segment1
--	...,
	lateNonCriticalExtension				OCTET STRING				OPTIONAL
}

-- ASN1STOP

SystemInformationBlockType12-r9 ::=	SEQUENCE {
	messageIdentifier-r9				BIT STRING (SIZE (16)),
	serialNumber-r9						BIT STRING (SIZE (16)),
	warningMessageSegmentType-r9		ENUMERATED {notLastSegment, lastSegment},
	warningMessageSegmentNumber-r9		INTEGER (0..63),
	warningMessageSegment-r9			OCTET STRING,
	dataCodingScheme-r9					OCTET STRING (SIZE (1)) 		OPTIONAL, 	-- Cond Segment1
	lateNonCriticalExtension			OCTET STRING					OPTIONAL,
	...
}

-- ASN1STOP

SystemInformationBlockType13-r9 ::=	SEQUENCE {
	mbsfn-AreaInfoList-r9				MBSFN-AreaInfoList-r9,
	notificationConfig-r9				MBMS-NotificationConfig-r9,
	lateNonCriticalExtension			OCTET STRING					OPTIONAL,
	...
}

-- ASN1STOP

SystemInformationBlockType14-r11 ::=	SEQUENCE {
	eab-Param-r11							CHOICE {
		eab-Common-r11							EAB-Config-r11,
		eab-PerPLMN-List-r11					SEQUENCE (SIZE (1..maxPLMN-r11)) OF EAB-ConfigPLMN-r11
	}														OPTIONAL, -- Need OR
	lateNonCriticalExtension				OCTET STRING			OPTIONAL,
	...
}

EAB-ConfigPLMN-r11 ::=				SEQUENCE {
	eab-Config-r11						EAB-Config-r11				OPTIONAL -- Need OR
}

EAB-Config-r11 ::=					SEQUENCE {
	eab-Category-r11					ENUMERATED {a, b, c},
	eab-BarringBitmap-r11				BIT STRING (SIZE (10))
}

-- ASN1STOP

SystemInformationBlockType15-r11 ::=	SEQUENCE {
	mbms-SAI-IntraFreq-r11					MBMS-SAI-List-r11				OPTIONAL,	-- Need OR
	mbms-SAI-InterFreqList-r11				MBMS-SAI-InterFreqList-r11		OPTIONAL,	-- Need OR
	lateNonCriticalExtension				OCTET STRING					OPTIONAL,
--	...,
	[[	mbms-SAI-InterFreqList-v1140		MBMS-SAI-InterFreqList-v1140	OPTIONAL	-- Cond InterFreq
	]]
}

MBMS-SAI-List-r11 ::=					SEQUENCE (SIZE (1..maxSAI-MBMS-r11)) OF MBMS-SAI-r11

MBMS-SAI-r11 ::=						INTEGER (0..65535)

MBMS-SAI-InterFreqList-r11 ::=			SEQUENCE (SIZE (1..maxFreq)) OF MBMS-SAI-InterFreq-r11

MBMS-SAI-InterFreqList-v1140 ::=		SEQUENCE (SIZE (1..maxFreq)) OF MBMS-SAI-InterFreq-v1140

MBMS-SAI-InterFreq-r11 ::=				SEQUENCE {
	dl-CarrierFreq-r11						ARFCN-ValueEUTRA-r9,
	mbms-SAI-List-r11						MBMS-SAI-List-r11
}

MBMS-SAI-InterFreq-v1140 ::=			SEQUENCE {
		multiBandInfoList-r11				MultiBandInfoList-r11			OPTIONAL	-- Need OR
}


-- ASN1STOP

SystemInformationBlockType16-r11 ::=		SEQUENCE {
	timeInfo-r11							SEQUENCE {
		timeInfoUTC-r11						INTEGER (0..549755813887),
		dayLightSavingTime-r11				BIT STRING (SIZE (2))		OPTIONAL,	-- Need OR
		leapSeconds-r11						INTEGER (-127..128)			OPTIONAL,	-- Need OR
		localTimeOffset-r11					INTEGER (-63..64)			OPTIONAL	-- Need OR
	}																	OPTIONAL,	-- Need OR
	lateNonCriticalExtension			OCTET STRING				OPTIONAL,
	...
}

-- ASN1STOP

SystemInformationBlockType17-r12 ::=	SEQUENCE {
	wlan-OffloadInfoPerPLMN-List-r12		SEQUENCE (SIZE (1..maxPLMN-r11)) OF
										 WLAN-OffloadInfoPerPLMN-r12			OPTIONAL, -- Need OR
	lateNonCriticalExtension				OCTET STRING				OPTIONAL,
	...
}

WLAN-OffloadInfoPerPLMN-r12 ::= 			SEQUENCE {
	 	wlan-OffloadConfigCommon-r12		WLAN-OffloadConfig-r12		OPTIONAL, 	-- Need OR
		wlan-Id-List-r12					WLAN-Id-List-r12			OPTIONAL,	-- Need OR
		...
}

WLAN-Id-List-r12 ::=				SEQUENCE (SIZE (1..maxWLAN-Id-r12)) OF WLAN-Identifiers-r12

WLAN-Identifiers-r12 ::=			SEQUENCE {
	ssid-r12						OCTET STRING (SIZE (1..32))		OPTIONAL, 	-- Need OR
	bssid-r12						OCTET STRING (SIZE (6)) 			OPTIONAL, 	-- Need OR
	hessid-r12						OCTET STRING (SIZE (6)) 			OPTIONAL, 	-- Need OR
	...
}

-- ASN1STOP

SystemInformationBlockType18-r12 ::= SEQUENCE {
	commConfig-r12						SEQUENCE {
		commRxPool-r12						SL-CommRxPoolList-r12,
		commTxPoolNormalCommon-r12			SL-CommTxPoolList-r12			OPTIONAL,	-- Need OR
		commTxPoolExceptional-r12			SL-CommTxPoolList-r12			OPTIONAL,	-- Need OR
		commSyncConfig-r12					SL-SyncConfigList-r12		OPTIONAL	-- Need OR
	}																		OPTIONAL,	-- Need OR
	lateNonCriticalExtension			OCTET STRING						OPTIONAL,
--	...,
	[[	commTxPoolNormalCommonExt-r13			SL-CommTxPoolListExt-r13	OPTIONAL,	-- Need OR
		commTxAllowRelayCommon-r13				ENUMERATED {true}			OPTIONAL	-- Need OR
	]]
}

-- ASN1STOP

SystemInformationBlockType19-r12 ::= SEQUENCE {
	discConfig-r12						SEQUENCE {
		discRxPool-r12						SL-DiscRxPoolList-r12,
		discTxPoolCommon-r12				SL-DiscTxPoolList-r12 			OPTIONAL,	-- Need OR
		discTxPowerInfo-r12				SL-DiscTxPowerInfoList-r12 	OPTIONAL,	-- Cond Tx
		discSyncConfig-r12					SL-SyncConfigList-r12		OPTIONAL	-- Need OR
	}																		OPTIONAL,	-- Need OR
	discInterFreqList-r12				SL-CarrierFreqInfoList-r12		OPTIONAL,	-- Need OR
	lateNonCriticalExtension			OCTET STRING						OPTIONAL,
--	...,
	[[	discConfig-v13x0				SEQUENCE {
			discInterFreqList-v13x0			SL-CarrierFreqInfoList-v13x0	OPTIONAL,	-- Need OR
			gapRequestsAllowedCommon		ENUMERATED {true}			OPTIONAL	-- Need OR
		}																OPTIONAL,	-- Need OR
		discConfigRelay-r13				SEQUENCE {
			discThreshHiRelayUE-r13			RSRP-Range					OPTIONAL,	-- Need OR
			discThreshLoRelayUE-r13			RSRP-Range					OPTIONAL,	-- Need OR
			discHystMaxRelayUE-r13			ENUMERATED {dB0, dB3, dB6, dB9, dB12, dBinf},
			discHystMinRelayUE-r13			ENUMERATED {dB0, dB3, dB6, dB9, dB12},
				-- Uu threshold
			discThreshHiRemoteUE-r13		RSRP-Range					OPTIONAL,	-- Need OR
			discHystMaxRemoteUE-r13			ENUMERATED {dB0, dB3, dB6, dB9, dB12},
				-- Uu threshold
			reselectionInfoRemoteUE-IC-r13	ReselectionInfoRelay-r13
		}																OPTIONAL,	-- Need OR
		discConfigPS-13					SEQUENCE {
			discRxPoolPS-r13				SL-DiscRxPoolList-r12,
			discTxPoolPS-Common-r13			SL-DiscTxPoolList-r12		OPTIONAL	-- Need OR
		}																OPTIONAL	-- Need OR
	]]
}

SL-CarrierFreqInfoList-r12 ::=	SEQUENCE (SIZE (1..maxFreq)) OF SL-CarrierFreqInfo-r12

SL-CarrierFreqInfoList-v13x0 ::=	SEQUENCE (SIZE (1..maxFreq)) OF SL-CarrierFreqInfo-v13x0

SL-CarrierFreqInfo-r12::= 		SEQUENCE {
	carrierFreq-r12 					ARFCN-ValueEUTRA-r9,
	plmn-IdentityList-r12			PLMN-IdentityList4-r12			OPTIONAL	-- Need OP
}

ReselectionInfoRelay-r13 ::=	SEQUENCE {
	q-RxLevMin-r13					Q-RxLevMin,
	-- Note that the mapping of invidual values may be different for PC5, but the granularity/
	-- number of values is same as for Uu
	filterCoefficient-r13			FilterCoefficient,
	minHyst-r13					ENUMERATED {dB0, dB3,
										dB6, dB9, dB12, dBinf}	OPTIONAL	-- Need OR
}

CellSelectionInfoNFreq-r13 ::=	SEQUENCE {
	-- Cell selection information as in SIB1
	q-RxLevMin-r13					Q-RxLevMin,
	q-RxLevMinOffset					INTEGER (1..8)			OPTIONAL,	-- Need OP
	-- Cell re-selection information as in SIB3
	q-Hyst-r13							ENUMERATED {
											dB0, dB1, dB2, dB3, dB4, dB5, dB6, dB8, dB10,
											dB12, dB14, dB16, dB18, dB20, dB22, dB24},
	q-RxLevMinReselection-r13			Q-RxLevMin			OPTIONAL,	-- Need OP
	t-ReselectionEUTRA-r13				T-Reselection
}

SL-CarrierFreqInfo-v13x0::= 	SEQUENCE {
	discRxResources-r13				SL-DiscRxPoolList-r12				OPTIONAL,	-- Need OR
	discRxResourcesPS-r13			SL-DiscRxPoolList-r12				OPTIONAL,	-- Need OR
	discTxResources-r13				SL-DiscTxResourcesInterFreq-r13		OPTIONAL,	-- Need OR
	discTxResourcesPS-r13			SL-DiscTxResourcesInterFreq-r13		OPTIONAL,	-- Need OR
	discTxPowerInfo-r13				SL-DiscTxPowerInfoList-r12 			OPTIONAL,	-- Cond Tx
	discTxRefCarrierCommon-r13		ENUMERATED {pCell}					OPTIONAL,	-- Need OR
	discSyncConfig-r13				SL-SyncConfigListNFreq-r12				OPTIONAL,	-- Need OR
	cellSelectionInfo-r13			CellSelectionInfoNFreq-r13			OPTIONAL	-- Need OR
}

PLMN-IdentityList4-r12 ::=	SEQUENCE (SIZE (1..maxPLMN-r11)) OF	PLMN-IdentityInfo2-r12

PLMN-IdentityInfo2-r12 ::=		CHOICE	{
	plmn-Index-r12					INTEGER (1..maxPLMN-r11),
	plmnIdentity-r12				PLMN-Identity
}

SL-DiscTxResourcesInterFreq-r13 ::=	CHOICE {
	acquireSI-FromCarrier-r13		NULL,
	discTxPoolCommon-r13			SL-DiscTxPoolList-r12,
	requestDedicated-r13			NULL,
	noTxOnCarrier-r13				NULL
}

-- ASN1STOP

SystemInformationBlockType20-r13 ::=	SEQUENCE {
	sc-mcch-RepetionPeriod-r13		ENUMERATED {rf2, rf4, rf8, rf16, rf32, rf64, rf128, rf256},
	sc-mcch-Offset-r13				INTEGER (0..10),
	sc-mcch-Subframe-r13			INTEGER (0..9),
	sc-mcch-ModificationPeriod-r13	ENUMERATED {rf2, rf4, rf8, rf16, rf32, rf64, rf128, rf256,
										 rf512, rf1024},
	lateNonCriticalExtension			OCTET STRING					OPTIONAL,
	...
}

-- ASN1STOP

AntennaInfoCommon ::=				SEQUENCE {
	antennaPortsCount					ENUMERATED {an1, an2, an4, spare1}
}

AntennaInfoDedicated ::=			SEQUENCE {
	transmissionMode					ENUMERATED {
											tm1, tm2, tm3, tm4, tm5, tm6,
											tm7, tm8-v920},
	codebookSubsetRestriction			CHOICE {
		n2TxAntenna-tm3						BIT STRING (SIZE (2)),
		n4TxAntenna-tm3						BIT STRING (SIZE (4)),
		n2TxAntenna-tm4						BIT STRING (SIZE (6)),
		n4TxAntenna-tm4						BIT STRING (SIZE (64)),
		n2TxAntenna-tm5						BIT STRING (SIZE (4)),
		n4TxAntenna-tm5						BIT STRING (SIZE (16)),
		n2TxAntenna-tm6						BIT STRING (SIZE (4)),
		n4TxAntenna-tm6						BIT STRING (SIZE (16))
	}		OPTIONAL, 															-- Cond TM
	ue-TransmitAntennaSelection			CHOICE{
		release							NULL,
		setup							ENUMERATED {closedLoop, openLoop}
	}
}

AntennaInfoDedicated-v920 ::=		SEQUENCE {
	codebookSubsetRestriction-v920		CHOICE {
		n2TxAntenna-tm8-r9					BIT STRING (SIZE (6)),
		n4TxAntenna-tm8-r9					BIT STRING (SIZE (32))
	}		OPTIONAL 															-- Cond TM8
}

AntennaInfoDedicated-r10 ::=		SEQUENCE {
	transmissionMode-r10				ENUMERATED {
											tm1, tm2, tm3, tm4, tm5, tm6, tm7, tm8-v920,
											tm9-v1020, tm10-v1130, spare6, spare5, spare4,
											spare3, spare2, spare1},
	codebookSubsetRestriction-r10		BIT STRING			OPTIONAL,			-- Cond TMX
	ue-TransmitAntennaSelection		CHOICE{
		release							NULL,
		setup							ENUMERATED {closedLoop, openLoop}
	}
}

AntennaInfoDedicated-v10i0::=	SEQUENCE {
	maxLayersMIMO-r10			ENUMERATED {twoLayers, fourLayers, eightLayers}		OPTIONAL	-- Need OR
}

AntennaInfoDedicated-v1250 ::=		SEQUENCE {
	alternativeCodebookEnabledFor4TX-r12	BOOLEAN
}

-- ASN1STOP

AntennaInfoUL-r10 ::=		SEQUENCE {
	transmissionModeUL-r10				ENUMERATED {tm1, tm2, spare6, spare5,
													spare4, spare3, spare2, spare1}	OPTIONAL,	-- Need OR
	fourAntennaPortActivated-r10			ENUMERATED {setup}			OPTIONAL		-- Need OR
}

-- ASN1STOP

CQI-ReportConfig ::=				SEQUENCE {
	cqi-ReportModeAperiodic			CQI-ReportModeAperiodic	OPTIONAL,			-- Need OR
	nomPDSCH-RS-EPRE-Offset				INTEGER (-1..6),
	cqi-ReportPeriodic				CQI-ReportPeriodic	OPTIONAL				-- Need ON
}

CQI-ReportConfig-v920 ::=		SEQUENCE {
	cqi-Mask-r9						ENUMERATED {setup}		OPTIONAL,		-- Cond cqi-Setup
	pmi-RI-Report-r9				ENUMERATED {setup}		OPTIONAL		-- Cond PMIRI
}

CQI-ReportConfig-r10 ::=	SEQUENCE {
	cqi-ReportAperiodic-r10				CQI-ReportAperiodic-r10			OPTIONAL,	-- Need ON
	nomPDSCH-RS-EPRE-Offset			INTEGER (-1..6),
	cqi-ReportPeriodic-r10				CQI-ReportPeriodic-r10			OPTIONAL,	-- Need ON
	pmi-RI-Report-r9					ENUMERATED {setup}				OPTIONAL,	-- Cond PMIRIPCell
	csi-SubframePatternConfig-r10		CHOICE {
		release							NULL,
		setup							SEQUENCE {
			csi-MeasSubframeSet1-r10			MeasSubframePattern-r10,
			csi-MeasSubframeSet2-r10			MeasSubframePattern-r10
		}
	}																	OPTIONAL	-- Need ON
}

CQI-ReportConfig-v1130 ::=	SEQUENCE {
	cqi-ReportPeriodic-v1130			CQI-ReportPeriodic-v1130,
	cqi-ReportBoth-r11					CQI-ReportBoth-r11
}

CQI-ReportConfig-v1250 ::=		SEQUENCE {
	csi-SubframePatternConfig-r12		CHOICE {
		release							NULL,
		setup							SEQUENCE {
			csi-MeasSubframeSets-r12			BIT STRING (SIZE (10))
		}
	}																OPTIONAL,	-- Need ON
	cqi-ReportBoth-v1250					CQI-ReportBoth-v1250		OPTIONAL, 	-- Need ON
	cqi-ReportAperiodic-v1250	CQI-ReportAperiodic-v1250		OPTIONAL,	-- Need ON
	altCQI-Table-r12			ENUMERATED {
									allSubframes, csi-SubframeSet1,
									csi-SubframeSet2, spare1}		OPTIONAL		-- Need OP
}

CQI-ReportConfig-v13xy ::=			SEQUENCE {
	cqi-ReportAperiodic-v13xy			CQI-ReportAperiodic-v13xy	OPTIONAL,		-- Need ON
	cqi-ReportPeriodic-v13xy			CQI-ReportPeriodic-v13xy 		OPTIONAL		-- Need ON
}

CQI-ReportConfigSCell-r10 ::=				SEQUENCE {
	cqi-ReportModeAperiodic-r10			CQI-ReportModeAperiodic OPTIONAL,			-- Need OR
	nomPDSCH-RS-EPRE-Offset-r10				INTEGER (-1..6),
	cqi-ReportPeriodicSCell-r10			CQI-ReportPeriodic-r10			OPTIONAL,	-- Need ON
	pmi-RI-Report-r10					ENUMERATED {setup}				OPTIONAL	-- Cond PMIRISCell
}

CQI-ReportConfigSCell-v13x0 ::=		SEQUENCE {
	cqi-ReportPeriodicSCell-v13x0			CQI-ReportPeriodic-v13xy
}

CQI-ReportPeriodic ::=		CHOICE {
	release							NULL,
	setup							SEQUENCE {
		cqi-PUCCH-ResourceIndex				INTEGER (0..1185),
		cqi-pmi-ConfigIndex					INTEGER (0..1023),
		cqi-FormatIndicatorPeriodic			CHOICE {
			widebandCQI							NULL,
			subbandCQI							SEQUENCE {
				k									INTEGER (1..4)
			}
		},
		ri-ConfigIndex						INTEGER (0..1023) 	OPTIONAL, 				-- Need OR
		simultaneousAckNackAndCQI			BOOLEAN
	}
}

CQI-ReportPeriodic-r10 ::=		CHOICE {
	release								NULL,
	setup								SEQUENCE {
		cqi-PUCCH-ResourceIndex-r10			INTEGER (0..1184),
		cqi-PUCCH-ResourceIndexP1-r10		INTEGER (0..1184)				OPTIONAL,	-- Need OR
		cqi-pmi-ConfigIndex				INTEGER (0..1023),
		cqi-FormatIndicatorPeriodic-r10		CHOICE {
			widebandCQI-r10						SEQUENCE {
				csi-ReportMode-r10		ENUMERATED {submode1, submode2}		OPTIONAL	-- Need OR
			},
			subbandCQI-r10						SEQUENCE {
				k								INTEGER (1..4),
				periodicityFactor-r10				ENUMERATED {n2, n4}
			}
		},
		ri-ConfigIndex					INTEGER (0..1023)		OPTIONAL,				-- Need OR
		simultaneousAckNackAndCQI		BOOLEAN,
		cqi-Mask-r9						ENUMERATED {setup}		OPTIONAL,				-- Need OR
		csi-ConfigIndex-r10				CHOICE {
			release							NULL,
			setup							SEQUENCE {
				cqi-pmi-ConfigIndex2-r10		INTEGER (0..1023),
				ri-ConfigIndex2-r10				INTEGER (0..1023)		OPTIONAL		-- Need OR
			}
		}		OPTIONAL																-- Need ON
	}
}


CQI-ReportPeriodic-v1130 ::=	SEQUENCE {
	simultaneousAckNackAndCQI-Format3-r11		ENUMERATED {setup}		OPTIONAL,	-- Need OR
	cqi-ReportPeriodicProcExtToReleaseList-r11	CQI-ReportPeriodicProcExtToReleaseList-r11	OPTIONAL,	-- Need ON
	cqi-ReportPeriodicProcExtToAddModList-r11	CQI-ReportPeriodicProcExtToAddModList-r11	OPTIONAL	-- Need ON
}

CQI-ReportPeriodic-v13xy ::=	SEQUENCE {
	cri-ReportConfig-r13			CRI-ReportConfig-r13				OPTIONAL,	-- Need ON
	simultaneousAckNackAndCQI-Format4-Format5-r13		ENUMERATED {setup}		OPTIONAL-- Need OR
}


CQI-ReportPeriodicProcExtToAddModList-r11 ::=		SEQUENCE (SIZE (1..maxCQI-ProcExt-r11)) OF CQI-ReportPeriodicProcExt-r11

CQI-ReportPeriodicProcExtToReleaseList-r11 ::=	SEQUENCE (SIZE (1..maxCQI-ProcExt-r11)) OF CQI-ReportPeriodicProcExtId-r11

CQI-ReportPeriodicProcExt-r11 ::=		SEQUENCE {
	cqi-ReportPeriodicProcExtId-r11	CQI-ReportPeriodicProcExtId-r11,
	cqi-pmi-ConfigIndex-r11			INTEGER (0..1023),
	cqi-FormatIndicatorPeriodic-r11	CHOICE {
		widebandCQI-r11				SEQUENCE {
			csi-ReportMode-r11			ENUMERATED {submode1, submode2}	OPTIONAL	-- Need OR
		},
		subbandCQI-r11				SEQUENCE {
			k							INTEGER (1..4),
			periodicityFactor-r11		ENUMERATED {n2, n4}
		}
	},
	ri-ConfigIndex-r11				INTEGER (0..1023)					OPTIONAL,	-- Need OR
	csi-ConfigIndex-r11				CHOICE {
		release							NULL,
		setup							SEQUENCE {
			cqi-pmi-ConfigIndex2-r11		INTEGER (0..1023),
			ri-ConfigIndex2-r11				INTEGER (0..1023)		OPTIONAL		-- Need OR
		}
	}																OPTIONAL,		-- Need ON
--	...,
	[[	cri-ReportConfig-r13			CRI-ReportConfig-r13				OPTIONAL	-- Need ON
	]]
}

CQI-ReportAperiodic-r10	::=		CHOICE {
	release								NULL,
	setup								SEQUENCE {
		cqi-ReportModeAperiodic-r10			CQI-ReportModeAperiodic,
		aperiodicCSI-Trigger-r10			SEQUENCE {	
			trigger1-r10					BIT STRING (SIZE (8)),
			trigger2-r10					BIT STRING (SIZE (8))
		}																	 OPTIONAL	-- Need OR
	}
}

CQI-ReportAperiodic-v1250	::=		CHOICE {
	release								NULL,
	setup								SEQUENCE {
		aperiodicCSI-Trigger-v1250			SEQUENCE {	
			trigger-SubframeSetIndicator-r12	ENUMERATED {s1, s2},
			trigger1-SubframeSetIndicator-r12	BIT STRING (SIZE (8)),
			trigger2-SubframeSetIndicator-r12	BIT STRING (SIZE (8))
		}
	}
}

CQI-ReportAperiodic-v13xy  	::=		CHOICE {
	release								NULL,
	setup								SEQUENCE {
		cqi-ReportModeAperiodic-r13		CQI-ReportModeAperiodic,
		aperiodicCSI-Trigger-v13xy			SEQUENCE {	
			trigger1-r13					BIT STRING (SIZE (32)),
			trigger2-r13					BIT STRING (SIZE (32)),
			trigger3-r13					BIT STRING (SIZE (32)),
			trigger4-r13					BIT STRING (SIZE (32)),
			trigger5-r13					BIT STRING (SIZE (32)),
			trigger6-r13					BIT STRING (SIZE (32))
		}																	 OPTIONAL,	-- Need OR
		aperiodicCSI-Trigger2-r13		SEQUENCE {	
			trigger1-SubframeSetIndicator-r13	BIT STRING (SIZE (32)),
			trigger2-SubframeSetIndicator-r13	BIT STRING (SIZE (32)),
			trigger3-SubframeSetIndicator-r13	BIT STRING (SIZE (32)),
			trigger4-SubframeSetIndicator-r13	BIT STRING (SIZE (32)),
			trigger5-SubframeSetIndicator-r13	BIT STRING (SIZE (32)),
			trigger6-SubframeSetIndicator-r13	BIT STRING (SIZE (32))
		}																	 OPTIONAL	-- Need OR
	}
}

CQI-ReportAperiodicProc-r11	::=		SEQUENCE {
	cqi-ReportModeAperiodic-r11			CQI-ReportModeAperiodic,
	trigger01-r11						BOOLEAN,
	trigger10-r11						BOOLEAN,
	trigger11-r11						BOOLEAN
}

CQI-ReportAperiodicProc-r13	::=		SEQUENCE {
	trigger001-r13						BOOLEAN,
	trigger010-r13						BOOLEAN,
	trigger011-r13						BOOLEAN,
	trigger100-r13						BOOLEAN,	
	trigger101-r13						BOOLEAN,
	trigger110-r13						BOOLEAN,
	trigger111-r13						BOOLEAN}

CQI-ReportModeAperiodic ::=				ENUMERATED {
											rm12, rm20, rm22, rm30, rm31,
											rm32-v1250, rm10-v13xy, rm11-v13xx
}

CQI-ReportBoth-r11 ::=			SEQUENCE {
	csi-IM-ConfigToReleaseList-r11		CSI-IM-ConfigToReleaseList-r11	OPTIONAL,	-- Need ON
	csi-IM-ConfigToAddModList-r11		CSI-IM-ConfigToAddModList-r11	OPTIONAL,	-- Need ON
	csi-ProcessToReleaseList-r11		CSI-ProcessToReleaseList-r11	OPTIONAL,	-- Need ON
	csi-ProcessToAddModList-r11			CSI-ProcessToAddModList-r11		OPTIONAL	-- Need ON
}

CQI-ReportBoth-v1250 ::=			SEQUENCE {
	csi-IM-ConfigToReleaseListExt-r12		CSI-IM-ConfigId-v1250	OPTIONAL,	-- Need ON
	csi-IM-ConfigToAddModListExt-r12		CSI-IM-ConfigExt-r12	OPTIONAL	-- Need ON
}

CSI-IM-ConfigToAddModList-r11 ::=		SEQUENCE (SIZE (1..maxCSI-IM-r11)) OF CSI-IM-Config-r11

CSI-IM-ConfigToReleaseList-r11 ::=		SEQUENCE (SIZE (1..maxCSI-IM-r11)) OF CSI-IM-ConfigId-r11

CSI-ProcessToAddModList-r11 ::=		SEQUENCE (SIZE (1..maxCSI-Proc-r11)) OF CSI-Process-r11

CSI-ProcessToReleaseList-r11 ::=	SEQUENCE (SIZE (1..maxCSI-Proc-r11)) OF CSI-ProcessId-r11

CQI-ReportBothProc-r11 ::=			SEQUENCE {
	ri-Ref-CSI-ProcessId-r11			CSI-ProcessId-r11				OPTIONAL,		-- Need OR
	pmi-RI-Report-r11					ENUMERATED {setup}				OPTIONAL		-- Need OR
}

CRI-ReportConfig-r13 ::=			CHOICE {
	release								NULL,
	setup								SEQUENCE {
		cri-ConfigIndex-r13					ENUMERATED {n1, n2, n4, n8, n16, n32},
		cri-ConfigIndex2-r13				ENUMERATED {n1, n2, n4, n8, n16, n32}	OPTIONAL	-- Need OR
	}
}

-- ASN1STOP

CQI-ReportPeriodicProcExtId-r11 ::=					INTEGER (1..maxCQI-ProcExt-r11)

-- ASN1STOP

CrossCarrierSchedulingConfig-r10 ::=		SEQUENCE {
	schedulingCellInfo-r10				CHOICE {
		own-r10								SEQUENCE {					-- No cross carrier scheduling
			cif-Presence-r10						BOOLEAN
		},
		other-r10								SEQUENCE {					-- Cross carrier scheduling
			schedulingCellId-r10				ServCellIndex-r10,
			pdsch-Start-r10						INTEGER (1..4)
		}
	}
}

CrossCarrierSchedulingConfig-r13 ::=		SEQUENCE {
	schedulingCellInfo-r13				CHOICE {
		own-r13								SEQUENCE {					-- No cross carrier scheduling
			cif-Presence-r13						BOOLEAN
		},
		other-r13							SEQUENCE {					-- Cross carrier scheduling
			schedulingCellId-r13				ServCellIndexFull-r13,
			pdsch-Start-r13						INTEGER (1..4),
			cif-InSchedulingCell-r13				INTEGER (1..7)
		}
	}
}

-- ASN1STOP

CSI-IM-Config-r11 ::=		SEQUENCE {
	csi-IM-ConfigId-r11			CSI-IM-ConfigId-r11,
	resourceConfig-r11			INTEGER (0..31),
	subframeConfig-r11			INTEGER (0..154),
	...
}

CSI-IM-ConfigExt-r12 ::=		SEQUENCE {
	csi-IM-ConfigId-v1250			CSI-IM-ConfigId-v1250,
	resourceConfig-r12			INTEGER (0..31),
	subframeConfig-r12			INTEGER (0..154),
	...
}

-- ASN1STOP

CSI-IM-ConfigId-r11 ::=					INTEGER (1..maxCSI-IM-r11)
CSI-IM-ConfigId-r12 ::=					INTEGER (1..maxCSI-IM-r12)
CSI-IM-ConfigId-v1250 ::=				INTEGER (maxCSI-IM-r12)

-- ASN1STOP

CSI-Process-r11 ::=		SEQUENCE {
	csi-ProcessId-r11			CSI-ProcessId-r11,
	csi-RS-ConfigNZPId-r11		CSI-RS-ConfigNZPId-r11,
	csi-IM-ConfigId-r11			CSI-IM-ConfigId-r11,
	p-C-AndCBSRList-r11	SEQUENCE (SIZE (1..2)) OF P-C-AndCBSR-r11,
	cqi-ReportBothProc-r11		CQI-ReportBothProc-r11			OPTIONAL,		-- Need OR
	cqi-ReportPeriodicProcId-r11	INTEGER (0..maxCQI-ProcExt-r11)		OPTIONAL,		-- Need OR
	cqi-ReportAperiodicProc-r11	CQI-ReportAperiodicProc-r11		OPTIONAL,		-- Need OR
--	...,
	[[	alternativeCodebookEnabledFor4TXProc-r12	ENUMERATED {true}	OPTIONAL,	-- Need ON
		csi-IM-ConfigIdList-r12		CHOICE {
			release						NULL,
			setup						SEQUENCE (SIZE (1..2)) OF CSI-IM-ConfigId-r12
		}														OPTIONAL,	-- Need ON
		cqi-ReportAperiodicProc2-r12	CHOICE {
			release						NULL,
			setup						CQI-ReportAperiodicProc-r11
		}														OPTIONAL	-- Need ON
	]],
	[[	cqi-ReportAperiodicProc-r13		CQI-ReportAperiodicProc-r13		OPTIONAL,		-- Need ON
		cqi-ReportAperiodicProc2-r13		CHOICE {
			release						NULL,
			setup						CQI-ReportAperiodicProc-r13
		}														OPTIONAL,		-- Need ON
		eMIMO-Type-r13				CHOICE {
			release						NULL,
			setup						CHOICE {
				nonPrecoded-r13				CSI-RS-InfoNonPrecoded-r13,
				beamformed-r13				CSI-RS-InfoBeamformed-r13
			}
		}														OPTIONAL	-- Need ON
	]]
}

P-C-AndCBSR-r11 ::=	SEQUENCE {
	p-C-r11						INTEGER (-8..15),
	codebookSubsetRestriction-r11	BIT STRING
}

P-C-AndCBSR-r13 ::=	SEQUENCE {
	legacySet						SEQUENCE {
		p-C-r11						INTEGER (-8..15),
		codebookSubsetRestriction1-r13	BIT STRING
	}												OPTIONAL,	-- Cond BeamformedKna
	codebookSubsetRestriction2-r13	BIT STRING		OPTIONAL,	-- Cond NonPreCoded
	codebookSubsetRestriction3-r13	BIT STRING		OPTIONAL	-- Cond BeamformedK1a
}

P-C-AndCBSR-PerResourceConfig-r13 ::=	SEQUENCE (SIZE (1..2)) OF P-C-AndCBSR-r13

-- ASN1STOP

CSI-ProcessId-r11 ::=		INTEGER (1..maxCSI-Proc-r11)

-- ASN1STOP

CSI-RS-Config-r10 ::=		SEQUENCE {
	csi-RS-r10					CHOICE {
		release						NULL,
		setup						SEQUENCE {
			antennaPortsCount-r10			ENUMERATED {an1, an2, an4, an8},
			resourceConfig-r10				INTEGER (0..31),
			subframeConfig-r10				INTEGER (0..154),
			p-C-r10							INTEGER (-8..15)
		}
	}																OPTIONAL,			-- Need ON
	zeroTxPowerCSI-RS-r10		ZeroTxPowerCSI-RS-Conf-r12			OPTIONAL			-- Need ON
}

CSI-RS-Config-v1250 ::=		SEQUENCE {
	zeroTxPowerCSI-RS2-r12		ZeroTxPowerCSI-RS-Conf-r12			OPTIONAL,			-- Need ON
	ds-ZeroTxPowerCSI-RS-r12		CHOICE {
		release							NULL,
		setup							SEQUENCE {
			zeroTxPowerCSI-RS-List-r12		SEQUENCE (SIZE (1..maxDS-ZTP-CSI-RS-r12)) OF ZeroTxPowerCSI-RS-r12
		}
	}																OPTIONAL				-- Need ON
}

CSI-RS-Config-v13x0 ::=		SEQUENCE {
	eMIMO-Type-r13				CHOICE {
		release						NULL,
		setup						CHOICE {
			nonPrecoded-r13				CSI-RS-InfoNonPrecoded-r13,
			beamformed-r13				CSI-RS-InfoBeamformed-r13
		}
	}														OPTIONAL	-- Need ON
}

ZeroTxPowerCSI-RS-Conf-r12 ::=	CHOICE {
		release							NULL,
		setup							ZeroTxPowerCSI-RS-r12 
}

ZeroTxPowerCSI-RS-r12 ::=	SEQUENCE {
	zeroTxPowerResourceConfigList-r12		BIT STRING (SIZE (16)),
	zeroTxPowerSubframeConfig-r12			INTEGER (0..154)
}

-- ASN1STOP

CSI-RS-ConfigNZP-r11 ::=		SEQUENCE {
	csi-RS-ConfigNZPId-r11			CSI-RS-ConfigNZPId-r11,
	antennaPortsCount-r11			ENUMERATED {an1, an2, an4, an8},
	resourceConfig-r11				INTEGER (0..31),
	subframeConfig-r11				INTEGER (0..154),
	scramblingIdentity-r11			INTEGER (0..503),
	qcl-CRS-Info-r11				SEQUENCE {
		qcl-ScramblingIdentity-r11		INTEGER (0..503),
		crs-PortsCount-r11				ENUMERATED {n1, n2, n4, spare1},
		mbsfn-SubframeConfigList-r11	CHOICE {
				release						NULL,
				setup						SEQUENCE {
					subframeConfigList			MBSFN-SubframeConfigList
				}
		}																OPTIONAL	-- Need ON
	}																	OPTIONAL,	-- Need OR
--	...,
	[[	eMIMO-Info-r13					CHOICE {
			release						NULL,
			setup						SEQUENCE {
				nzp-resourceConfigList-r13		SEQUENCE (SIZE (2..8)) OF ResourceConfig-r13,
				cdmType							ENUMERATED {cdm2, cdm4}	OPTIONAL	-- Need OR
			}
		}																OPTIONAL	-- Need ON
	]]
}

ResourceConfig-r13 ::=				INTEGER (0..31)

-- ASN1STOP

CSI-RS-ConfigNZPId-r11 ::=					INTEGER (1..maxCSI-RS-NZP-r11)

-- ASN1STOP

CSI-RS-ConfigZP-r11 ::=		SEQUENCE {
	csi-RS-ConfigZPId-r11		CSI-RS-ConfigZPId-r11,
	resourceConfigList-r11		BIT STRING (SIZE (16)),
	subframeConfig-r11			INTEGER (0..154),
	...
}

-- ASN1STOP

CSI-RS-ConfigZPId-r11 ::=					INTEGER (1..maxCSI-RS-ZP-r11)

-- ASN1STOP

CSI-RS-InfoNonPrecoded-r13 ::=			SEQUENCE {
	p-C-AndCBSRList-r13						SEQUENCE (SIZE (1..2)) OF P-C-AndCBSR-r13	OPTIONAL,	-- Need OR
	codebookConfigN1-r13					ENUMERATED {an1, an2, an3, an4, an8},
	codebookConfigN2-r13					ENUMERATED {an1, an2, an3, an4, an8},
	codebookOverSamplingRateConfig-O1-r13	ENUMERATED {na,an4,an8},
	codebookOverSamplingRateConfig-O2-r13	ENUMERATED {na,an4,an8},
	codebookConfig-r13						ENUMERATED {an1, an2, an3, an4},
	interferenceMeasRestriction-r13			ENUMERATED {on}			OPTIONAL	-- Need OR
}

CSI-RS-InfoBeamformed-r13::=			SEQUENCE	{
	csi-RS-ConfigNZPIdListExt-r13 			SEQUENCE (SIZE (1..7)) OF CSI-RS-ConfigNZPId-r11	OPTIONAL,	-- Need OR
	csi-IM-ConfigIdListExt-r13				SEQUENCE (SIZE (1..7)) OF CSI-IM-ConfigIdInfo-r13	OPTIONAL,	-- Need OR
	p-C-AndCBSR-PerResourceConfigList-r13	SEQUENCE (SIZE (1..7)) OF P-C-AndCBSR-PerResourceConfig-r13	OPTIONAL,	-- Need OR
	alternativeCodebookEnabledBeamformed-r13	ENUMERATED {true}	OPTIONAL,	-- Need OR
	channelMeasRestriction-r13				ENUMERATED {on}			OPTIONAL	-- Need OR
}

CSI-IM-ConfigIdInfo-r13 ::=	SEQUENCE {
	csi-IM-ConfigId-r13					CSI-IM-ConfigId-r11		OPTIONAL,
	interferenceMeasRestriction-r13			ENUMERATED {on} 		OPTIONAL	-- Need OR
}

-- ASN1STOP

DMRS-Config-r11 ::=		CHOICE {
	release						NULL,
	setup						SEQUENCE {
		scramblingIdentity-r11		INTEGER (0..503),
		scramblingIdentity2-r11		INTEGER (0..503)
	}
}
DMRS-Config-v13x0 ::=			SEQUENCE {
		dmrs-tableAlt-r13				ENUMERATED {true}			OPTIONAL	-- Need OR
}

-- ASN1STOP

DRB-Identity ::=					INTEGER (1..32)

-- ASN1STOP

EPDCCH-Config-r11 ::=		SEQUENCE{
	config-r11		CHOICE {
		release						NULL,
			setup						SEQUENCE {
			subframePatternConfig-r11	CHOICE {
				release						NULL,
				setup						SEQUENCE {
					subframePattern-r11			MeasSubframePattern-r10
				}
			}																	OPTIONAL, -- Need ON
			startSymbol-r11				INTEGER (1..4)							OPTIONAL, -- Need OP
			setConfigToReleaseList-r11	EPDCCH-SetConfigToReleaseList-r11		OPTIONAL, -- Need ON
			setConfigToAddModList-r11	EPDCCH-SetConfigToAddModList-r11		OPTIONAL -- Need ON
		}
	}
}

EPDCCH-SetConfigToAddModList-r11 ::=	SEQUENCE (SIZE(1..maxEPDCCH-Set-r11)) OF EPDCCH-SetConfig-r11

EPDCCH-SetConfigToReleaseList-r11 ::=	SEQUENCE (SIZE(1..maxEPDCCH-Set-r11)) OF EPDCCH-SetConfigId-r11

EPDCCH-SetConfig-r11 ::=		SEQUENCE {
	setConfigId-r11					EPDCCH-SetConfigId-r11,
	transmissionType-r11			ENUMERATED {localised, distributed},
	resourceBlockAssignment-r11		SEQUENCE{
		numberPRB-Pairs-r11				ENUMERATED {n2, n4, n8},
		resourceBlockAssignment-r11		BIT STRING (SIZE(4..38))
	},
	dmrs-ScramblingSequenceInt-r11	INTEGER (0..503),
	pucch-ResourceStartOffset-r11	INTEGER (0..2047),
	re-MappingQCL-ConfigId-r11		PDSCH-RE-MappingQCL-ConfigId-r11	OPTIONAL, -- Need OR
--	...,
	[[	csi-RS-ConfigZPId2-r12				CHOICE {
			release						NULL,
			setup						CSI-RS-ConfigZPId-r11
		}															OPTIONAL	-- Need ON
	]]
}

EPDCCH-SetConfigId-r11 ::=	INTEGER (0..1)

-- ASN1STOP
EIMTA-MainConfig-r12 ::=	CHOICE {
	release							NULL,
	setup							SEQUENCE {
		eimta-RNTI-r12				C-RNTI,
		eimta-CommandPeriodicity-r12	ENUMERATED {sf10, sf20, sf40, sf80},
		eimta-CommandSubframeSet-r12	BIT STRING (SIZE(10))
	}
}

EIMTA-MainConfigServCell-r12 ::=	CHOICE {
	release								NULL,
	setup								SEQUENCE {
		eimta-UL-DL-ConfigIndex-r12				INTEGER (1..5),
		eimta-HARQ-ReferenceConfig-r12		ENUMERATED {sa2,sa4,sa5},
		mbsfn-SubframeConfigList-v1250		CHOICE {
				release								NULL,
				setup								SEQUENCE {
				subframeConfigList-r12				MBSFN-SubframeConfigList
				}
		}
	}
}

-- ASN1STOP

LogicalChannelConfig ::=			SEQUENCE {
	ul-SpecificParameters				SEQUENCE {
		priority							INTEGER (1..16),
		prioritisedBitRate					ENUMERATED {
												kBps0, kBps8, kBps16, kBps32, kBps64, kBps128,
												kBps256, infinity, kBps512-v1020, kBps1024-v1020,
												kBps2048-v1020, spare5, spare4, spare3, spare2,
												spare1},
		bucketSizeDuration					ENUMERATED {
												ms50, ms100, ms150, ms300, ms500, ms1000, spare2,
												spare1},
		logicalChannelGroup					INTEGER (0..3)			OPTIONAL			-- Need OR
	}		OPTIONAL,																	-- Cond UL
--	...,
	[[	logicalChannelSR-Mask-r9			ENUMERATED {setup}		OPTIONAL		-- Cond SRmask
	]],
	[[	logicalChannelSR-Prohibit-r12		BOOLEAN					OPTIONAL		-- Need ON
	]]
}

-- ASN1STOP

MAC-MainConfig ::=					SEQUENCE {
	ul-SCH-Config						SEQUENCE {
		maxHARQ-Tx							ENUMERATED {
												n1, n2, n3, n4, n5, n6, n7, n8,
												n10, n12, n16, n20, n24, n28,
												spare2, spare1}		OPTIONAL,	-- Need ON
		periodicBSR-Timer					PeriodicBSR-Timer-r12	OPTIONAL,	-- Need ON
		retxBSR-Timer						RetxBSR-Timer-r12,
		ttiBundling							BOOLEAN
	}																OPTIONAL, 	-- Need ON
	drx-Config							DRX-Config					OPTIONAL,	-- Need ON
	timeAlignmentTimerDedicated			TimeAlignmentTimer,
	phr-Config							CHOICE {
		release								NULL,
		setup								SEQUENCE {
			periodicPHR-Timer					ENUMERATED {sf10, sf20, sf50, sf100, sf200,
															sf500, sf1000, infinity},
			prohibitPHR-Timer					ENUMERATED {sf0, sf10, sf20, sf50, sf100,
																sf200, sf500, sf1000},
			dl-PathlossChange					ENUMERATED {dB1, dB3, dB6, infinity}
		}
	}																OPTIONAL,	-- Need ON
--	...,
	[[	sr-ProhibitTimer-r9					INTEGER (0..7)			OPTIONAL	-- Need ON
	]],
	[[	mac-MainConfig-v1020				SEQUENCE {
			sCellDeactivationTimer-r10			ENUMERATED {
													rf2, rf4, rf8, rf16, rf32, rf64, rf128,
													spare}			OPTIONAL,	-- Need OP
			extendedBSR-Sizes-r10				ENUMERATED {setup}		OPTIONAL,	-- Need OR
			extendedPHR-r10						ENUMERATED {setup}		OPTIONAL	-- Need OR
		}															OPTIONAL	-- Need ON
	]],
	[[	stag-ToReleaseList-r11				STAG-ToReleaseList-r11	OPTIONAL,	-- Need ON
		stag-ToAddModList-r11				STAG-ToAddModList-r11	OPTIONAL,	-- Need ON
		drx-Config-v1130					DRX-Config-v1130		OPTIONAL	-- Need ON
	]],
	[[	e-HARQ-Pattern-r12					BOOLEAN					OPTIONAL,	-- Need ON
		dualConnectivityPHR					CHOICE {
			release								NULL,
			setup								SEQUENCE {
				phr-ModeOtherCG-r12					ENUMERATED {real, virtual}
			}
		}														OPTIONAL,	-- Need ON
		logicalChannelSR-Config-r12		CHOICE {
			release								NULL,
			setup								SEQUENCE {
				logicalChannelSR-ProhibitTimer-r12		ENUMERATED {sf20, sf40, sf64, sf128, sf512, sf1024, sf2560, spare1}
			}
		}															OPTIONAL		-- Need ON
	]],
	[[	extendedPHR2-r13					ENUMERATED {setup}		OPTIONAL,		-- Need ON 
		eDRX-Config-CycleStartOffset-r13 	CHOICE {
			release							NULL,
			setup
											CHOICE {
			sf5120									INTEGER(0..1),
			sf10240									INTEGER(0..3)
			}
		}										OPTIONAL	-- Need ON
	]]
}

MAC-MainConfigSCell-r11 ::=			SEQUENCE {
	stag-Id-r11							STAG-Id-r11		OPTIONAL,	-- Need OP
	...
}

DRX-Config ::=						CHOICE {
	release								NULL,
	setup								SEQUENCE {
		onDurationTimer						ENUMERATED {
												psf1, psf2, psf3, psf4, psf5, psf6,
												psf8, psf10, psf20, psf30, psf40,
												psf50, psf60, psf80, psf100,
												psf200},
		drx-InactivityTimer					ENUMERATED {
												psf1, psf2, psf3, psf4, psf5, psf6,
												psf8, psf10, psf20, psf30, psf40,
												psf50, psf60, psf80, psf100,
												psf200, psf300, psf500, psf750,
												psf1280, psf1920, psf2560, psf0-v1020,
												spare9, spare8, spare7, spare6,
												spare5, spare4, spare3, spare2,
												spare1},
		drx-RetransmissionTimer				ENUMERATED {
												psf1, psf2, psf4, psf6, psf8, psf16,
												psf24, psf33},
		longDRX-CycleStartOffset		CHOICE {
			sf10							INTEGER(0..9),
			sf20							INTEGER(0..19),
			sf32							INTEGER(0..31),
			sf40							INTEGER(0..39),
			sf64							INTEGER(0..63),
			sf80							INTEGER(0..79),
			sf128							INTEGER(0..127),
			sf160							INTEGER(0..159),
			sf256							INTEGER(0..255),
			sf320							INTEGER(0..319),
			sf512							INTEGER(0..511),
			sf640							INTEGER(0..639),
			sf1024							INTEGER(0..1023),
			sf1280							INTEGER(0..1279),
			sf2048							INTEGER(0..2047),
			sf2560							INTEGER(0..2559)
		},
		shortDRX							SEQUENCE {
			shortDRX-Cycle						ENUMERATED	{
													sf2, sf5, sf8, sf10, sf16, sf20,
													sf32, sf40, sf64, sf80, sf128, sf160,
													sf256, sf320, sf512, sf640},
			drxShortCycleTimer					INTEGER (1..16)
		}		OPTIONAL													-- Need OR
	}
}

DRX-Config-v1130 ::=					SEQUENCE {
	drx-RetransmissionTimer-v1130			ENUMERATED {psf0-v1130}	OPTIONAL,	--Need OR
	longDRX-CycleStartOffset-v1130			CHOICE {
		sf60-v1130								INTEGER(0..59),
		sf70-v1130								INTEGER(0..69)
	}																OPTIONAL,	--Need OR
	shortDRX-Cycle-v1130					ENUMERATED	{sf4-v1130}	OPTIONAL	--Need OR
}

PeriodicBSR-Timer-r12 ::=					ENUMERATED {
												sf5, sf10, sf16, sf20, sf32, sf40, sf64, sf80,
												sf128, sf160, sf320, sf640, sf1280, sf2560,
												infinity, spare1}

RetxBSR-Timer-r12 ::=							ENUMERATED {
												sf320, sf640, sf1280, sf2560, sf5120,
												sf10240, spare2, spare1}

STAG-ToReleaseList-r11 ::=	SEQUENCE (SIZE (1..maxSTAG-r11)) OF STAG-Id-r11

STAG-ToAddModList-r11 ::=	SEQUENCE (SIZE (1..maxSTAG-r11)) OF STAG-ToAddMod-r11

STAG-ToAddMod-r11 ::=		SEQUENCE {
	stag-Id-r11					STAG-Id-r11,
	timeAlignmentTimerSTAG-r11	TimeAlignmentTimer,
	...
}

STAG-Id-r11::=				INTEGER (1..maxSTAG-r11)

-- ASN1STOP

PDCCH-ConfigSCell-r13 ::=		SEQUENCE {
	skipMonitoringDCI-format0-1A-r13	ENUMERATED {true}				OPTIONAL,	-- Need OR
	pdcch-candidateReductions-r13		PDCCH-CandidateReductions-r13		OPTIONAL 	-- Need OR
}

PDCCH-CandidateReductionValue-r13 ::= ENUMERATED {n0, n33, n66, n100}

PDCCH-CandidateReductions-r13 ::= SEQUENCE {
	pdcch-candidateReductionAL1		PDCCH-CandidateReductionValue-r13,
	pdcch-candidateReductionAL2		PDCCH-CandidateReductionValue-r13,
	pdcch-candidateReductionAL3		PDCCH-CandidateReductionValue-r13,
	pdcch-candidateReductionAL4		PDCCH-CandidateReductionValue-r13,
	pdcch-candidateReductionAL5		PDCCH-CandidateReductionValue-r13 
}

-- ASN1STOP

PDCP-Config ::=						SEQUENCE {
	discardTimer						ENUMERATED {
											ms50, ms100, ms150, ms300, ms500,
											ms750, ms1500, infinity
	}															OPTIONAL,			-- Cond Setup
	rlc-AM								SEQUENCE {
		statusReportRequired				BOOLEAN
	}															OPTIONAL,			-- Cond Rlc-AM
	rlc-UM								SEQUENCE {
		pdcp-SN-Size						ENUMERATED {len7bits, len12bits}
	}															OPTIONAL,			-- Cond Rlc-UM
	headerCompression					CHOICE {
		notUsed								NULL,
		rohc								SEQUENCE {
			maxCID								INTEGER (1..16383)				DEFAULT 15,
			profiles							SEQUENCE {
				profile0x0001						BOOLEAN,
				profile0x0002						BOOLEAN,
				profile0x0003						BOOLEAN,
				profile0x0004						BOOLEAN,
				profile0x0006						BOOLEAN,
				profile0x0101						BOOLEAN,
				profile0x0102						BOOLEAN,
				profile0x0103						BOOLEAN,
				profile0x0104						BOOLEAN
			},
			...
		}
	},
--	...,
	[[	rn-IntegrityProtection-r10		ENUMERATED {enabled}	OPTIONAL	-- Cond RN
	]],
	[[	pdcp-SN-Size-v1130				ENUMERATED {len15bits}	OPTIONAL	-- Cond Rlc-AM2
	]],
	[[	ul-DataSplitDRB-ViaSCG-r12		BOOLEAN		OPTIONAL,	-- Need ON
		t-Reordering-r12				ENUMERATED {
										ms0, ms20, ms40, ms60, ms80, ms100, ms120, ms140,
										ms160, ms180, ms200, ms220, ms240, ms260, ms280, ms300,
										ms500, ms750, spare14, spare13, spare12, spare11, spare10,
										spare9, spare8, spare7, spare6, spare5, spare4, spare3,
										spare2, spare1}					OPTIONAL	-- Cond SetupS
	]],
	[[	ul-DataSplitThreshold-r13		CHOICE {
			release						NULL,
			setup						ENUMERATED {
										b0, b100, b200, b400, b800, b1600, b3200, b6400, b12800,
										b25600, b51200, b102400, b204800, b409600, b819200,
										spare1}
		}																OPTIONAL,	-- Need ON
		pdcp-SN-Size-v13xx				ENUMERATED {len18bits}	OPTIONAL	-- Cond Rlc-AM3
	]]

}

-- ASN1STOP

PDSCH-ConfigCommon ::=		SEQUENCE {
	referenceSignalPower				INTEGER (-60..50),
	p-b									INTEGER (0..3)
}

PDSCH-ConfigDedicated::=		SEQUENCE {
	p-a									ENUMERATED {
											dB-6, dB-4dot77, dB-3, dB-1dot77,
											dB0, dB1, dB2, dB3}
}

PDSCH-ConfigDedicated-v1130 ::=		SEQUENCE {
	dmrs-ConfigPDSCH-r11				DMRS-Config-r11					OPTIONAL,	-- Need ON
	qcl-Operation						ENUMERATED {typeA, typeB}			OPTIONAL,	-- Need OR
	re-MappingQCLConfigToReleaseList-r11	RE-MappingQCLConfigToReleaseList-r11	OPTIONAL,	-- Need ON
	re-MappingQCLConfigToAddModList-r11		RE-MappingQCLConfigToAddModList-r11		OPTIONAL	-- Need ON
}

PDSCH-ConfigDedicated-v1280 ::=		SEQUENCE {
	tbsIndexAlt-r12						ENUMERATED {a26, a33}				OPTIONAL	-- Need OR
}

PDSCH-ConfigDedicated-v13x0 ::=		SEQUENCE {
	dmrs-ConfigPDSCH-v13x0				DMRS-Config-v13x0					OPTIONAL	-- Need ON
}

RE-MappingQCLConfigToAddModList-r11 ::=		SEQUENCE (SIZE (1..maxRE-MapQCL-r11)) OF PDSCH-RE-MappingQCL-Config-r11

RE-MappingQCLConfigToReleaseList-r11 ::=	SEQUENCE (SIZE (1..maxRE-MapQCL-r11)) OF PDSCH-RE-MappingQCL-ConfigId-r11

PDSCH-RE-MappingQCL-Config-r11 ::=		SEQUENCE {
	pdsch-RE-MappingQCL-ConfigId-r11	PDSCH-RE-MappingQCL-ConfigId-r11,
	optionalSetOfFields-r11				SEQUENCE {
		crs-PortsCount-r11					ENUMERATED {n1, n2, n4, spare1},
		crs-FreqShift-r11					INTEGER (0..5),
		mbsfn-SubframeConfigList-r11		CHOICE {
			release								NULL,
			setup								SEQUENCE {
				subframeConfigList					MBSFN-SubframeConfigList
			}
		}																	OPTIONAL,	-- Need ON
		pdsch-Start-r11						ENUMERATED {reserved, n1, n2, n3, n4, assigned}
	}																		OPTIONAL,	-- Need OP
	csi-RS-ConfigZPId-r11				CSI-RS-ConfigZPId-r11,
	qcl-CSI-RS-ConfigNZPId-r11			CSI-RS-ConfigNZPId-r11				OPTIONAL,	-- Need OR
	...
}

-- ASN1STOP

PDSCH-RE-MappingQCL-ConfigId-r11 ::=		INTEGER (1..maxRE-MapQCL-r11)

-- ASN1STOP

PHICH-Config ::=					SEQUENCE {
	phich-Duration						ENUMERATED {normal, extended},
	phich-Resource						ENUMERATED {oneSixth, half, one, two}
}

-- ASN1STOP

PhysicalConfigDedicated ::=		SEQUENCE {
	pdsch-ConfigDedicated				PDSCH-ConfigDedicated			OPTIONAL,		-- Need ON
	pucch-ConfigDedicated				PUCCH-ConfigDedicated			OPTIONAL,		-- Need ON
	pusch-ConfigDedicated				PUSCH-ConfigDedicated			OPTIONAL,		-- Need ON
	uplinkPowerControlDedicated			UplinkPowerControlDedicated		OPTIONAL,		-- Need ON
	tpc-PDCCH-ConfigPUCCH				TPC-PDCCH-Config 				OPTIONAL,		-- Need ON
	tpc-PDCCH-ConfigPUSCH				TPC-PDCCH-Config 				OPTIONAL,		-- Need ON
	cqi-ReportConfig					CQI-ReportConfig				OPTIONAL,		-- Cond CQI-r8
	soundingRS-UL-ConfigDedicated		SoundingRS-UL-ConfigDedicated	OPTIONAL,		-- Need ON
	antennaInfo							CHOICE {
		explicitValue						AntennaInfoDedicated,
		defaultValue						NULL
	}		OPTIONAL,																-- Cond AI-r8
	schedulingRequestConfig				SchedulingRequestConfig		OPTIONAL, 			-- Need ON
--	...,
	[[	cqi-ReportConfig-v920				CQI-ReportConfig-v920		OPTIONAL,		-- Cond CQI-r8
		antennaInfo-v920					AntennaInfoDedicated-v920	OPTIONAL		-- Cond AI-r8
	]],
	[[	antennaInfo-r10					CHOICE {
			explicitValue-r10				AntennaInfoDedicated-r10,
			defaultValue					NULL
		}		OPTIONAL,															-- Cond AI-r10
		antennaInfoUL-r10				AntennaInfoUL-r10				OPTIONAL,		-- Need ON
		cif-Presence-r10				BOOLEAN							OPTIONAL,	-- Need ON
		cqi-ReportConfig-r10			CQI-ReportConfig-r10			OPTIONAL,		-- Cond CQI-r10
		csi-RS-Config-r10				CSI-RS-Config-r10				OPTIONAL,		-- Need ON
		pucch-ConfigDedicated-v1020		PUCCH-ConfigDedicated-v1020		OPTIONAL,		-- Need ON
		pusch-ConfigDedicated-v1020		PUSCH-ConfigDedicated-v1020		OPTIONAL,		-- Need ON
		schedulingRequestConfig-v1020	SchedulingRequestConfig-v1020	OPTIONAL,		-- Need ON
		soundingRS-UL-ConfigDedicated-v1020
								SoundingRS-UL-ConfigDedicated-v1020		OPTIONAL,		-- Need ON
		soundingRS-UL-ConfigDedicatedAperiodic-r10
								SoundingRS-UL-ConfigDedicatedAperiodic-r10	OPTIONAL,	-- Need ON
		uplinkPowerControlDedicated-v1020	UplinkPowerControlDedicated-v1020	OPTIONAL	-- Need ON
	]],
	[[	additionalSpectrumEmissionCA-r10 			CHOICE {
			release									NULL,
			setup									SEQUENCE {
				additionalSpectrumEmissionPCell-r10		AdditionalSpectrumEmission
			}
		}			OPTIONAL	-- Need ON
	]],
	[[	-- DL configuration as well as configuration applicable for DL and UL
		csi-RS-ConfigNZPToReleaseList-r11	CSI-RS-ConfigNZPToReleaseList-r11	OPTIONAL,	-- Need ON
		csi-RS-ConfigNZPToAddModList-r11	CSI-RS-ConfigNZPToAddModList-r11	OPTIONAL,	-- Need ON
		csi-RS-ConfigZPToReleaseList-r11	CSI-RS-ConfigZPToReleaseList-r11	OPTIONAL,	-- Need ON
		csi-RS-ConfigZPToAddModList-r11		CSI-RS-ConfigZPToAddModList-r11	OPTIONAL,	-- Need ON
		epdcch-Config-r11					EPDCCH-Config-r11				OPTIONAL,	-- Need ON
		pdsch-ConfigDedicated-v1130			PDSCH-ConfigDedicated-v1130		OPTIONAL,	-- Need ON
	-- UL configuration
		cqi-ReportConfig-v1130				CQI-ReportConfig-v1130			OPTIONAL,	-- Need ON
		pucch-ConfigDedicated-v1130			PUCCH-ConfigDedicated-v1130		OPTIONAL,	-- Need ON
		pusch-ConfigDedicated-v1130			PUSCH-ConfigDedicated-v1130		OPTIONAL,	-- Need ON
		uplinkPowerControlDedicated-v1130	UplinkPowerControlDedicated-v1130	OPTIONAL	-- Need ON
	]],
	[[	antennaInfo-v1250					AntennaInfoDedicated-v1250		OPTIONAL,	-- Cond AI-r10
		eimta-MainConfig-r12				EIMTA-MainConfig-r12			OPTIONAL,	-- Need ON
		eimta-MainConfigPCell-r12			EIMTA-MainConfigServCell-r12		OPTIONAL,	-- Need ON
		pucch-ConfigDedicated-v1250			PUCCH-ConfigDedicated-v1250		OPTIONAL,	-- Need ON
		cqi-ReportConfigPCell-v1250			CQI-ReportConfig-v1250			OPTIONAL,	-- Need ON
		uplinkPowerControlDedicated-v1250	UplinkPowerControlDedicated-v1250	OPTIONAL,	-- Need ON
		pusch-ConfigDedicated-v1250		PUSCH-ConfigDedicated-v1250		OPTIONAL,	-- Need ON
		csi-RS-Config-v1250					CSI-RS-Config-v1250				OPTIONAL	-- Need ON
	]],
	[[	pdsch-ConfigDedicated-v1280			PDSCH-ConfigDedicated-v1280		OPTIONAL	-- Need ON
	]],
	[[	pdsch-ConfigDedicated-v13x0			PDSCH-ConfigDedicated-v13x0		OPTIONAL,	-- Need ON
		pucch-ConfigDedicated-r13			PUCCH-ConfigDedicated-v13xy		OPTIONAL,	-- Need ON
		pusch-ConfigDedicated-r13			PUSCH-ConfigDedicated-v13xy		OPTIONAL,	-- Need ON
		cqi-ReportConfig-v13xy					CQI-ReportConfig-v13xy		OPTIONAL,	-- Need ON
		soundingRS-UL-ConfigDedicated-v13x0
								SoundingRS-UL-ConfigDedicated-v13x0		OPTIONAL,		-- Need ON
		soundingRS-UL-ConfigDedicatedUpPTsExt-r13
								SoundingRS-UL-ConfigDedicatedUpPTsExt-r13		OPTIONAL,		-- Need ON
		soundingRS-UL-ConfigDedicatedAperiodic-v13x0
								SoundingRS-UL-ConfigDedicatedAperiodic-v13x0	OPTIONAL,	-- Need ON
		soundingRS-UL-ConfigDedicatedAperiodicUpPTsExt-r13
								SoundingRS-UL-ConfigDedicatedAperiodicUpPTsExt-r13		OPTIONAL,		-- Need ON
		cqi-ReportConfigPCell-v13x0			CQI-ReportConfig-v13xy			OPTIONAL,	-- Need ON
		csi-RS-Config-v13x0					CSI-RS-Config-v13x0				OPTIONAL	-- Need ON
	]]
}

PhysicalConfigDedicatedSCell-r10 ::=		SEQUENCE {
	-- DL configuration as well as configuration applicable for DL and UL
	nonUL-Configuration-r10					SEQUENCE {
		antennaInfo-r10							AntennaInfoDedicated-r10	OPTIONAL,	-- Need ON
		crossCarrierSchedulingConfig-r10		CrossCarrierSchedulingConfig-r10	OPTIONAL,	-- Need ON
		csi-RS-Config-r10						CSI-RS-Config-r10			OPTIONAL,	-- Need ON
		pdsch-ConfigDedicated-r10				PDSCH-ConfigDedicated		OPTIONAL	-- Need ON
	}																OPTIONAL, 	-- Cond SCellAdd
	-- UL configuration
	ul-Configuration-r10					SEQUENCE {
		antennaInfoUL-r10						AntennaInfoUL-r10			OPTIONAL,	-- Need ON
		pusch-ConfigDedicatedSCell-r10			PUSCH-ConfigDedicatedSCell-r10		OPTIONAL,	-- Need ON
		uplinkPowerControlDedicatedSCell-r10	UplinkPowerControlDedicatedSCell-r10	OPTIONAL,	-- Need ON
		cqi-ReportConfigSCell-r10				CQI-ReportConfigSCell-r10	OPTIONAL,	-- Need ON
		soundingRS-UL-ConfigDedicated-r10		SoundingRS-UL-ConfigDedicated	OPTIONAL,	-- Need ON
		soundingRS-UL-ConfigDedicated-v1020
								SoundingRS-UL-ConfigDedicated-v1020	OPTIONAL,		-- Need ON
		soundingRS-UL-ConfigDedicatedAperiodic-r10
								SoundingRS-UL-ConfigDedicatedAperiodic-r10	OPTIONAL	-- Need ON
	}																	OPTIONAL,	-- Cond CommonUL
--	...,
	[[	-- DL configuration as well as configuration applicable for DL and UL
		csi-RS-ConfigNZPToReleaseList-r11	CSI-RS-ConfigNZPToReleaseList-r11	OPTIONAL,	-- Need ON
		csi-RS-ConfigNZPToAddModList-r11	CSI-RS-ConfigNZPToAddModList-r11	OPTIONAL,	-- Need ON
		csi-RS-ConfigZPToReleaseList-r11	CSI-RS-ConfigZPToReleaseList-r11	OPTIONAL,	-- Need ON
		csi-RS-ConfigZPToAddModList-r11		CSI-RS-ConfigZPToAddModList-r11	OPTIONAL,	-- Need ON
		epdcch-Config-r11					EPDCCH-Config-r11				OPTIONAL,	-- Need ON
		pdsch-ConfigDedicated-v1130			PDSCH-ConfigDedicated-v1130		OPTIONAL,	-- Need ON
	-- UL configuration
		cqi-ReportConfig-v1130				CQI-ReportConfig-v1130			OPTIONAL,	-- Need ON
		pusch-ConfigDedicated-v1130				PUSCH-ConfigDedicated-v1130	OPTIONAL,	-- Need ON
		uplinkPowerControlDedicatedSCell-v1130	UplinkPowerControlDedicated-v1130	OPTIONAL	-- Need ON
	]],
	[[	antennaInfo-v1250					AntennaInfoDedicated-v1250		OPTIONAL,	-- Need ON
		eimta-MainConfigSCell-r12			EIMTA-MainConfigServCell-r12	OPTIONAL,	-- Need ON
		cqi-ReportConfigSCell-v1250			CQI-ReportConfig-v1250			OPTIONAL,	-- Need ON 
		uplinkPowerControlDedicatedSCell-v1250	UplinkPowerControlDedicated-v1250	OPTIONAL,	-- Need ON
		csi-RS-Config-v1250					CSI-RS-Config-v1250				OPTIONAL	-- Need ON
	]],
	[[	pdsch-ConfigDedicated-v1280			PDSCH-ConfigDedicated-v1280		OPTIONAL	-- Need ON
	]],
	[[	pucch-ConfigDedicated-r13			PUCCH-ConfigDedicated		OPTIONAL,	-- Need ON
		pucch-ConfigDedicatedExt1-r13		PUCCH-ConfigDedicated-v1020	OPTIONAL,	-- Need ON
		pucch-ConfigDedicatedExt2-r13		PUCCH-ConfigDedicated-v1130	OPTIONAL,	-- Need ON
		pucch-ConfigDedicatedExt3-r13		PUCCH-ConfigDedicated-v1250	OPTIONAL,	-- Cond eimta
		pucch-ConfigDedicatedExt4-r13		PUCCH-ConfigDedicated-v13xy	OPTIONAL,	-- Need ON
		pucch-Cell-r13						ENUMERATED {true}			OPTIONAL,	-- Cond PUCCH_SCell
		crossCarrierSchedulingConfig-r13	CrossCarrierSchedulingConfig-r13	 OPTIONAL,	-- Cond Cross-Carrier-Config
		schedulingRequestConfig-r13			SchedulingRequestConfig		OPTIONAL,		-- Need ON
		schedulingRequestConfigExt-r13		SchedulingRequestConfig-v1020	OPTIONAL,	-- Need ON
		tpc-PDCCH-ConfigPUCCH-SCell-r13		TPC-PDCCH-ConfigSCell		OPTIONAL,	-- Cond PUCCH-SCell
		pusch-ConfigDedicated-r13			PUSCH-ConfigDedicated		OPTIONAL,	-- Cond PUSCH-SCell
		pusch-ConfigDedicatedExt-r13		PUSCH-ConfigDedicated-v1020	OPTIONAL,	-- Cond PUSCH-SCell
		pusch-ConfigDedicatedExt2-r13		PUSCH-ConfigDedicated-v13xy	OPTIONAL,	-- Cond PUSCH-SCell
		uplinkPowerControlDedicated-r13		UplinkPowerControlDedicated	OPTIONAL,	-- Cond UL-Power-SCell
		uplinkPowerControlDedicatedExt-r13	UplinkPowerControlDedicated-v1020	OPTIONAL,	-- Cond UL-Power-SCell
		pdcch-ConfigSCell-r13				PDCCH-ConfigSCell-r13		OPTIONAL,	-- Need ON
		cqi-ReportConfig-v13xy					CQI-ReportConfig-v13xy				OPTIONAL,	-- Need ON
		pdsch-ConfigDedicated-v13x0			PDSCH-ConfigDedicated-v13x0		OPTIONAL,	-- Need ON
		soundingRS-UL-ConfigDedicated-v13x0
								SoundingRS-UL-ConfigDedicated-v13x0		OPTIONAL,		-- Need ON
		soundingRS-UL-ConfigDedicatedUpPTsExt-r13
								SoundingRS-UL-ConfigDedicatedUpPTsExt-r13		OPTIONAL,		-- Need ON
		soundingRS-UL-ConfigDedicatedAperiodic-v13x0
								SoundingRS-UL-ConfigDedicatedAperiodic-v13x0	OPTIONAL,	-- Need ON
		soundingRS-UL-ConfigDedicatedAperiodicUpPTsExt-r13
								SoundingRS-UL-ConfigDedicatedAperiodicUpPTsExt-r13		OPTIONAL,		-- Need ON
		csi-RS-Config-v13x0					CSI-RS-Config-v13x0				OPTIONAL,	-- Need ON
		laa-SCellConfiguration-r13		LAA-SCellConfiguration-r13		OPTIONAL	-- Need ON
	]]
}

LAA-SCellConfiguration-r13 ::=			SEQUENCE {
	subframeStartPosition				ENUMERATED {s0, s07},
	laa-SCellSubframeConfig				BIT STRING (SIZE(8))
}

CSI-RS-ConfigNZPToAddModList-r11 ::=	SEQUENCE (SIZE (1..maxCSI-RS-NZP-r11)) OF CSI-RS-ConfigNZP-r11

CSI-RS-ConfigNZPToReleaseList-r11 ::=	SEQUENCE (SIZE (1..maxCSI-RS-NZP-r11)) OF CSI-RS-ConfigNZPId-r11

CSI-RS-ConfigZPToAddModList-r11 ::=	SEQUENCE (SIZE (1..maxCSI-RS-ZP-r11)) OF CSI-RS-ConfigZP-r11

CSI-RS-ConfigZPToReleaseList-r11 ::=	SEQUENCE (SIZE (1..maxCSI-RS-ZP-r11)) OF CSI-RS-ConfigZPId-r11

-- ASN1STOP

P-Max ::=				INTEGER (-30..33)

-- ASN1STOP

PRACH-ConfigSIB ::=				SEQUENCE {
	rootSequenceIndex					INTEGER (0..837),
	prach-ConfigInfo					PRACH-ConfigInfo
}

PRACH-Config ::=					SEQUENCE {
	rootSequenceIndex					INTEGER (0..837),
	prach-ConfigInfo					PRACH-ConfigInfo					OPTIONAL	-- Need ON
}

PRACH-ConfigSCell-r10 ::=				SEQUENCE {
	prach-ConfigIndex-r10					INTEGER (0..63)
}

PRACH-ConfigInfo ::=				SEQUENCE {
	prach-ConfigIndex					INTEGER (0..63),
	highSpeedFlag						BOOLEAN,
	zeroCorrelationZoneConfig			INTEGER (0..15),
	prach-FreqOffset					INTEGER (0..94)
}

-- ASN1STOP

PresenceAntennaPort1 ::=				BOOLEAN

-- ASN1STOP

PUCCH-ConfigCommon ::=				SEQUENCE {
	deltaPUCCH-Shift					ENUMERATED {ds1, ds2, ds3},
	nRB-CQI								INTEGER (0..98),
	nCS-AN								INTEGER (0..7),
	n1PUCCH-AN							INTEGER (0..2047)
}

PUCCH-ConfigDedicated ::=			SEQUENCE {
	ackNackRepetition					CHOICE{
		release								NULL,
		setup								SEQUENCE {
			repetitionFactor					ENUMERATED {n2, n4, n6, spare1},
			n1PUCCH-AN-Rep						INTEGER (0..2047)
		}
	},
	tdd-AckNackFeedbackMode				ENUMERATED {bundling, multiplexing}	OPTIONAL	-- Cond TDD
}

PUCCH-ConfigDedicated-v1020 ::=		SEQUENCE {
	pucch-Format-r10					CHOICE {
		format3-r10								SEQUENCE {
			n3PUCCH-AN-List-r10	SEQUENCE (SIZE (1..4)) OF INTEGER (0..549)	OPTIONAL,	-- Need ON
			twoAntennaPortActivatedPUCCH-Format3-r10		CHOICE {	
				release											NULL,
				setup											SEQUENCE {
					n3PUCCH-AN-ListP1-r10	SEQUENCE (SIZE (1..4)) OF INTEGER (0..549)
				}
			}																OPTIONAL	-- Need ON
		},
		channelSelection-r10				SEQUENCE {
			n1PUCCH-AN-CS-r10					CHOICE {
				release								NULL,
				setup								SEQUENCE {
					n1PUCCH-AN-CS-List-r10				SEQUENCE (SIZE (1..2)) OF N1PUCCH-AN-CS-r10
				}
			}																OPTIONAL	-- Need ON
		}
	}																		OPTIONAL,	-- Need OR
	twoAntennaPortActivatedPUCCH-Format1a1b-r10		ENUMERATED {true}		OPTIONAL,	-- Need OR
	simultaneousPUCCH-PUSCH-r10						ENUMERATED {true}		OPTIONAL,	-- Need OR
	n1PUCCH-AN-RepP1-r10							INTEGER (0..2047)		OPTIONAL	-- Need OR
}

PUCCH-ConfigDedicated-v1130 ::=		SEQUENCE {
	n1PUCCH-AN-CS-v1130					CHOICE {
		release								NULL,
		setup								SEQUENCE {
			n1PUCCH-AN-CS-ListP1-r11			SEQUENCE (SIZE (2..4)) OF INTEGER (0..2047)
		}
	}																		OPTIONAL,	-- Need ON
	nPUCCH-Param-r11					CHOICE {
		release								NULL,
		setup								SEQUENCE {
			nPUCCH-Identity-r11					INTEGER (0..503),
			n1PUCCH-AN-r11						INTEGER (0..2047)
		}
	}																		OPTIONAL	-- Need ON
}

PUCCH-ConfigDedicated-v1250 ::=		SEQUENCE {
	nkaPUCCH-Param-r12					CHOICE {
		release								NULL,
		setup								SEQUENCE {
			nkaPUCCH-AN-r12						INTEGER (0..2047)
		}
	}
}

PUCCH-ConfigDedicated-v13xy ::=		SEQUENCE {
	spatialBundlingPUCCH				BOOLEAN,
	spatialBundlingPUSCH				BOOLEAN,
	harq-TimingTDD						BOOLEAN,
	codebooksizeDetermination-r13		INTEGER(0..1),
	maximumPayloadCoderate-r13			INTEGER (0..7), 	 
	pucch-Format-r13					CHOICE {
		format4-r13							SEQUENCE {
			format4-resourceConfiguration			SEQUENCE (SIZE (4)) OF Format4-resource-r13,
			format4-MultiCSI-resourceConfiguration	SEQUENCE (SIZE (1..2)) OF Format4-resource-r13 OPTIONAL 	-- Need OR
		},
		format5-r13				SEQUENCE {
			format5-resourceConfiguration			SEQUENCE (SIZE (4)) OF Format5-resource-r13,
			format5-MultiCSI-resourceConfiguration	SEQUENCE (SIZE (1..2)) OF Format5-resource-r13 OPTIONAL 	-- Need OR

		}
	}															OPTIONAL	-- Need OR
}

Format4-resource-r13	::=				SEQUENCE {
	startingPRB-format4-r13	  					INTEGER (0..109),
	numberOfPRB-format4-r13  					INTEGER (0..7)
}
 
Format5-resource-r13	::=				SEQUENCE {
	startingPRB-format5-r13	  					INTEGER (0..109),
	cdm-index-format5-r13  						INTEGER (0..1)
}



N1PUCCH-AN-CS-r10	::= SEQUENCE (SIZE (1..4)) OF INTEGER (0..2047)

-- ASN1STOP

PUSCH-ConfigCommon ::=				SEQUENCE {
	pusch-ConfigBasic					SEQUENCE {
		n-SB								INTEGER (1..4),
		hoppingMode							ENUMERATED {interSubFrame, intraAndInterSubFrame},
		pusch-HoppingOffset					INTEGER (0..98),
		enable64QAM							BOOLEAN
	},
	ul-ReferenceSignalsPUSCH			UL-ReferenceSignalsPUSCH
}

PUSCH-ConfigCommon-v1270 ::=		SEQUENCE {
	enable64QAM-v1270						ENUMERATED {true}
}

PUSCH-ConfigDedicated ::=			SEQUENCE {
	betaOffset-ACK-Index				INTEGER (0..15),
	betaOffset-RI-Index					INTEGER (0..15),
	betaOffset-CQI-Index				INTEGER (0..15)
}

PUSCH-ConfigDedicated-v1020 ::=		SEQUENCE {
	betaOffsetMC-r10					SEQUENCE {	
		betaOffset-ACK-Index-MC-r10			INTEGER (0..15),
		betaOffset-RI-Index-MC-r10			INTEGER (0..15),
		betaOffset-CQI-Index-MC-r10			INTEGER (0..15)
	}																		OPTIONAL,	-- Need OR
	groupHoppingDisabled-r10			ENUMERATED {true}					OPTIONAL,	-- Need OR
	dmrs-WithOCC-Activated-r10			ENUMERATED {true}					OPTIONAL	-- Need OR
}

PUSCH-ConfigDedicated-v1130 ::=		SEQUENCE {
	pusch-DMRS-r11						CHOICE {
		release								NULL,
		setup								SEQUENCE {
			nPUSCH-Identity-r11					INTEGER (0..509),
			nDMRS-CSH-Identity-r11				INTEGER (0..509)
		}
	}
}

PUSCH-ConfigDedicated-v1250::=			SEQUENCE {
	uciOnPUSCH				CHOICE {
		release					NULL,
		setup					SEQUENCE {
			betaOffset-ACK-Index-SubframeSet2-r12				INTEGER (0..15),
			betaOffset-RI-Index-SubframeSet2-r12				INTEGER (0..15),
			betaOffset-CQI-Index-SubframeSet2-r12				INTEGER (0..15),
			betaOffsetMC-r12					SEQUENCE {	
				betaOffset-ACK-Index-MC-SubframeSet2-r12			INTEGER (0..15),
				betaOffset-RI-Index-MC-SubframeSet2-r12			INTEGER (0..15),
				betaOffset-CQI-Index-MC-SubframeSet2-r12			INTEGER (0..15)
			}																OPTIONAL	-- Need OR
		}
	}
}

PUSCH-ConfigDedicated-v13xy ::=			SEQUENCE {
	betaOffset-r13								SEQUENCE {	
		betaOffset-ACK-Index-r13					INTEGER (0..15),
		betaOffset2-ACK-Index-r13					INTEGER (0..15)
	}																	OPTIONAL,	-- Need OR
	betaOffsetMC-r13							SEQUENCE {	
		betaOffset-ACK-Index-MC-r13					INTEGER (0..15),
		betaOffset2-ACK-Index-MC-r13				INTEGER (0..15)
	}																	OPTIONAL,	-- Need OR
	betaOffset-Subframeset2-r13					SEQUENCE {	
		betaOffset-ACK-Index-SubframeSet2-r13		INTEGER (0..15),
		betaOffset2-ACK-Index-SubframeSet2-r13		INTEGER (0..15)
	}																	OPTIONAL,	-- Need OR
	betaOffset-Subframeset2-MC-r13				SEQUENCE {	
		betaOffset-ACK-Index-MC-SubframeSet2-r13	INTEGER (0..15),
		betaOffset2-ACK-Index-MC-SubframeSet2-r13	INTEGER (0..15)
	}																	OPTIONAL	-- Need OR
}

PUSCH-ConfigDedicatedSCell-r10 ::=		SEQUENCE {
	groupHoppingDisabled-r10				ENUMERATED {true}				OPTIONAL,	-- Need OR
	dmrs-WithOCC-Activated-r10				ENUMERATED {true}				OPTIONAL	-- Need OR
}

UL-ReferenceSignalsPUSCH ::=		SEQUENCE {
	groupHoppingEnabled					BOOLEAN,
	groupAssignmentPUSCH				INTEGER (0..29),
	sequenceHoppingEnabled				BOOLEAN,
	cyclicShift							INTEGER (0..7)
}

-- ASN1STOP

RACH-ConfigCommon ::=		SEQUENCE {
	preambleInfo						SEQUENCE {
		numberOfRA-Preambles				ENUMERATED {
												n4, n8, n12, n16 ,n20, n24, n28,
												n32, n36, n40, n44, n48, n52, n56,
												n60, n64},
		preamblesGroupAConfig				SEQUENCE {
			sizeOfRA-PreamblesGroupA			ENUMERATED {
													n4, n8, n12, n16 ,n20, n24, n28,
													n32, n36, n40, n44, n48, n52, n56,
													n60},
			messageSizeGroupA					ENUMERATED {b56, b144, b208, b256},
			messagePowerOffsetGroupB			ENUMERATED {
													minusinfinity, dB0, dB5, dB8, dB10, dB12,
													dB15, dB18},
			...
		}			OPTIONAL													-- Need OP
	},
	powerRampingParameters				PowerRampingParameters,
	ra-SupervisionInfo					SEQUENCE {
		preambleTransMax					PreambleTransMax,
		ra-ResponseWindowSize				ENUMERATED {
												sf2, sf3, sf4, sf5, sf6, sf7,
												sf8, sf10},
		mac-ContentionResolutionTimer		ENUMERATED {
												sf8, sf16, sf24, sf32, sf40, sf48,
												sf56, sf64}
	},
	maxHARQ-Msg3Tx						INTEGER (1..8),
	...
}

RACH-ConfigCommon-v1250 ::=		SEQUENCE {
	txFailParams-r12 				SEQUENCE {
		connEstFailCount-r12					ENUMERATED {n1, n2, n3, n4},
		connEstFailOffsetValidity-r12			ENUMERATED {s30, s60, s120, s240, 
														s300, s420, s600, s900},
		connEstFailOffset-r12					INTEGER (0..15)		OPTIONAL	-- Need OP
	}
}

RACH-ConfigCommonSCell-r11 ::=		SEQUENCE {
	powerRampingParameters-r11				PowerRampingParameters,
	ra-SupervisionInfo-r11					SEQUENCE {
		preambleTransMax-r11					PreambleTransMax
	},
	...
}

PowerRampingParameters ::=			SEQUENCE {
	powerRampingStep					ENUMERATED {dB0, dB2,dB4, dB6},
	preambleInitialReceivedTargetPower	ENUMERATED {
											dBm-120, dBm-118, dBm-116, dBm-114, dBm-112,
											dBm-110, dBm-108, dBm-106, dBm-104, dBm-102,
											dBm-100, dBm-98, dBm-96, dBm-94,
											dBm-92, dBm-90}
}

PreambleTransMax ::=				ENUMERATED {
											n3, n4, n5, n6, n7,	n8, n10, n20, n50,
											n100, n200}

-- ASN1STOP

RACH-ConfigDedicated ::=		SEQUENCE {
	ra-PreambleIndex					INTEGER (0..63),
	ra-PRACH-MaskIndex					INTEGER (0..15)
}

-- ASN1STOP

RadioResourceConfigCommonSIB ::=	SEQUENCE {
	rach-ConfigCommon					RACH-ConfigCommon,
	bcch-Config 						BCCH-Config,
	pcch-Config 						PCCH-Config,
	prach-Config						PRACH-ConfigSIB,
	pdsch-ConfigCommon					PDSCH-ConfigCommon,
	pusch-ConfigCommon					PUSCH-ConfigCommon,
	pucch-ConfigCommon					PUCCH-ConfigCommon,
	soundingRS-UL-ConfigCommon			SoundingRS-UL-ConfigCommon,
	uplinkPowerControlCommon			UplinkPowerControlCommon,
	ul-CyclicPrefixLength				UL-CyclicPrefixLength,
--	...,
	[[	uplinkPowerControlCommon-v1020	UplinkPowerControlCommon-v1020		OPTIONAL	-- Need OR
	]],
	[[	rach-ConfigCommon-v1250			RACH-ConfigCommon-v1250		OPTIONAL	-- Need OR
	]],
	[[	pusch-ConfigCommon-v1270		PUSCH-ConfigCommon-v1270		OPTIONAL		-- Need OR
	]]
}

RadioResourceConfigCommon ::=		SEQUENCE {
	rach-ConfigCommon					RACH-ConfigCommon					OPTIONAL,	-- Need ON
	prach-Config						PRACH-Config,
	pdsch-ConfigCommon					PDSCH-ConfigCommon					OPTIONAL,	-- Need ON
	pusch-ConfigCommon					PUSCH-ConfigCommon,
	phich-Config						PHICH-Config						OPTIONAL,	-- Need ON
	pucch-ConfigCommon					PUCCH-ConfigCommon					OPTIONAL,	-- Need ON
	soundingRS-UL-ConfigCommon			SoundingRS-UL-ConfigCommon			OPTIONAL,	-- Need ON
	uplinkPowerControlCommon			UplinkPowerControlCommon			OPTIONAL,	-- Need ON
	antennaInfoCommon					AntennaInfoCommon			OPTIONAL,	-- Need ON
	p-Max								P-Max								OPTIONAL,	-- Need OP
	tdd-Config							TDD-Config							OPTIONAL,	-- Cond TDD
	ul-CyclicPrefixLength				UL-CyclicPrefixLength,
--	...,
	[[	uplinkPowerControlCommon-v1020	UplinkPowerControlCommon-v1020		OPTIONAL	-- Need ON
	]],
	[[	tdd-Config-v1130				TDD-Config-v1130				OPTIONAL	-- Cond TDD3
	]],
	[[	pusch-ConfigCommon-v1270		PUSCH-ConfigCommon-v1270		OPTIONAL		-- Need OR
	]],
	[[	uplinkPowerControlCommon-v13xy	UplinkPowerControlCommon-v13xy		OPTIONAL	-- Need ON
	]]
}

RadioResourceConfigCommonPSCell-r12 ::=	SEQUENCE {
	basicFields-r12						RadioResourceConfigCommonSCell-r10,
	pucch-ConfigCommon-r12				PUCCH-ConfigCommon,
	rach-ConfigCommon-r12				RACH-ConfigCommon,
	uplinkPowerControlCommonPSCell-r12	UplinkPowerControlCommonPSCell-r12,
--	...,
	[[	uplinkPowerControlCommon-v13xy	UplinkPowerControlCommon-v13xy		OPTIONAL	-- Need ON
	]]
}

RadioResourceConfigCommonSCell-r10 ::=	SEQUENCE {
	-- DL configuration as well as configuration applicable for DL and UL
	nonUL-Configuration-r10					SEQUENCE {
		-- 1: Cell characteristics
		dl-Bandwidth-r10						ENUMERATED {n6, n15, n25, n50, n75, n100},
		-- 2: Physical configuration, general
		antennaInfoCommon-r10					AntennaInfoCommon,
		mbsfn-SubframeConfigList-r10			MBSFN-SubframeConfigList	OPTIONAL,	-- Need OR
		-- 3: Physical configuration, control
		phich-Config-r10						PHICH-Config,
		-- 4: Physical configuration, physical channels
		pdsch-ConfigCommon-r10					PDSCH-ConfigCommon,
		tdd-Config-r10							TDD-Config					OPTIONAL	-- Cond TDDSCell
	},
	-- UL configuration
	ul-Configuration-r10						SEQUENCE {
		ul-FreqInfo-r10						SEQUENCE {
			ul-CarrierFreq-r10					ARFCN-ValueEUTRA			OPTIONAL,	-- Need OP
			ul-Bandwidth-r10					ENUMERATED {n6, n15,
													n25, n50, n75, n100}	OPTIONAL,	-- Need OP
			additionalSpectrumEmissionSCell-r10		AdditionalSpectrumEmission
		},
		p-Max-r10							P-Max						OPTIONAL,	-- Need OP
		uplinkPowerControlCommonSCell-r10		UplinkPowerControlCommonSCell-r10,
		-- A special version of IE UplinkPowerControlCommon may be introduced
		-- 3: Physical configuration, control
		soundingRS-UL-ConfigCommon-r10		SoundingRS-UL-ConfigCommon,
		ul-CyclicPrefixLength-r10			UL-CyclicPrefixLength,
		-- 4: Physical configuration, physical channels
		prach-ConfigSCell-r10					PRACH-ConfigSCell-r10		OPTIONAL,	-- Cond TDD-OR-NoR11
		pusch-ConfigCommon-r10				PUSCH-ConfigCommon
	}																	OPTIONAL,	-- Need OR
--	...,
	[[	ul-CarrierFreq-v1090				ARFCN-ValueEUTRA-v9e0			OPTIONAL	-- Need OP
	]],
	[[	rach-ConfigCommonSCell-r11			RACH-ConfigCommonSCell-r11		OPTIONAL,	-- Cond ULSCell
		prach-ConfigSCell-r11				PRACH-Config					OPTIONAL,	-- Cond UL
		tdd-Config-v1130					TDD-Config-v1130			OPTIONAL,	-- Cond TDD2
		uplinkPowerControlCommonSCell-v1130
								UplinkPowerControlCommonSCell-v1130	OPTIONAL	-- Cond UL
	]],
	[[	pusch-ConfigCommon-v1270		PUSCH-ConfigCommon-v1270		OPTIONAL		-- Need OR
	]],
	[[	pucch-ConfigCommon-r13				PUCCH-ConfigCommon		OPTIONAL,	-- Cond UL
		uplinkPowerControlCommonSCell-v13xx	UplinkPowerControlCommonPSCell-r12	OPTIONAL	-- Cond UL
	]]
}

BCCH-Config ::=						SEQUENCE {
	modificationPeriodCoeff				ENUMERATED {n2, n4, n8, n16}
}

PCCH-Config ::=						SEQUENCE {
	defaultPagingCycle					ENUMERATED {
											rf32, rf64, rf128, rf256},
	nB									ENUMERATED {
											fourT, twoT, oneT, halfT, quarterT, oneEighthT,
											oneSixteenthT, oneThirtySecondT}
}

UL-CyclicPrefixLength ::=			ENUMERATED {len1, len2}

-- ASN1STOP

RadioResourceConfigDedicated ::=		SEQUENCE {
	srb-ToAddModList					SRB-ToAddModList			OPTIONAL, 		-- Cond HO-Conn
	drb-ToAddModList					DRB-ToAddModList			OPTIONAL, 		-- Cond HO-toEUTRA
	drb-ToReleaseList					DRB-ToReleaseList			OPTIONAL, 		-- Need ON
	mac-MainConfig						CHOICE {
			explicitValue					MAC-MainConfig,
			defaultValue					NULL
	}		OPTIONAL,																-- Cond HO-toEUTRA2
	sps-Config							SPS-Config 					OPTIONAL,		-- Need ON
	physicalConfigDedicated				PhysicalConfigDedicated		OPTIONAL,		-- Need ON
--	...,
	[[	rlf-TimersAndConstants-r9		RLF-TimersAndConstants-r9			OPTIONAL	-- Need ON
	]],
	[[	measSubframePatternPCell-r10	MeasSubframePatternPCell-r10		OPTIONAL	-- Need ON
	]],
	[[	neighCellsCRS-Info-r11			NeighCellsCRS-Info-r11				OPTIONAL	-- Need ON
	]],
	[[	naics-Info-r12				NAICS-AssistanceInfo-r12			OPTIONAL	-- Need ON
	]],
	[[	neighCellsCRS-Info-r13			NeighCellsCRS-Info-r13				OPTIONAL	-- Cond CRSIM
	]]
}

RadioResourceConfigDedicatedPSCell-r12 ::=		SEQUENCE {
	-- UE specific configuration extensions applicable for an PSCell
	physicalConfigDedicatedPSCell-r12		PhysicalConfigDedicated		OPTIONAL,	-- Need ON
	sps-Config-r12							SPS-Config					OPTIONAL,	-- Need ON
	naics-Info-r12							NAICS-AssistanceInfo-r12	OPTIONAL,	-- Need ON
--	...,
	[[	neighCellsCRS-InfoPSCell-r13		NeighCellsCRS-Info-r13		OPTIONAL	-- Need ON
	]]
}

RadioResourceConfigDedicatedSCG-r12 ::=		SEQUENCE {
	drb-ToAddModListSCG-r12				DRB-ToAddModListSCG-r12			OPTIONAL, 	-- Need ON
	mac-MainConfigSCG-r12				MAC-MainConfig					OPTIONAL,	-- Need ON
	rlf-TimersAndConstantsSCG-r12		RLF-TimersAndConstantsSCG-r12	OPTIONAL,	-- Need ON
	...
}

RadioResourceConfigDedicatedSCell-r10 ::=	SEQUENCE {
	-- UE specific configuration extensions applicable for an SCell
	physicalConfigDedicatedSCell-r10		PhysicalConfigDedicatedSCell-r10	OPTIONAL,	-- Need ON
--	...,
	[[	mac-MainConfigSCell-r11			MAC-MainConfigSCell-r11			OPTIONAL	-- Cond SCellAdd
	]],
	[[	naics-Info-r12				NAICS-AssistanceInfo-r12		OPTIONAL	-- Need ON
	]],
	[[	neighCellsCRS-InfoSCell-r13			NeighCellsCRS-Info-r13		OPTIONAL	-- Need ON
	]]

}

SRB-ToAddModList ::=				SEQUENCE (SIZE (1..2)) OF SRB-ToAddMod

SRB-ToAddMod ::=	SEQUENCE {
	srb-Identity						INTEGER (1..2),
	rlc-Config							CHOICE {
		explicitValue						RLC-Config,
		defaultValue						NULL
	}		OPTIONAL,																-- Cond Setup
	logicalChannelConfig				CHOICE {
		explicitValue						LogicalChannelConfig,
		defaultValue						NULL
	}		OPTIONAL,																-- Cond Setup
	...
}

DRB-ToAddModList ::=				SEQUENCE (SIZE (1..maxDRB)) OF DRB-ToAddMod

DRB-ToAddModListSCG-r12 ::=		SEQUENCE (SIZE (1..maxDRB)) OF DRB-ToAddModSCG-r12

DRB-ToAddMod ::=	SEQUENCE {
	eps-BearerIdentity					INTEGER (0..15)			OPTIONAL,		-- Cond DRB-Setup
	drb-Identity						DRB-Identity,
	pdcp-Config							PDCP-Config				OPTIONAL,		-- Cond PDCP
	rlc-Config							RLC-Config				OPTIONAL,		-- Cond SetupM
	logicalChannelIdentity				INTEGER (3..10)			OPTIONAL,		-- Cond DRB-SetupM
	logicalChannelConfig				LogicalChannelConfig	OPTIONAL,		-- Cond SetupM
--	...,
	[[	drb-TypeChange-r12						ENUMERATED {toMCG}	OPTIONAL,		-- Need OP
		rlc-Config-v1250					RLC-Config-v1250		OPTIONAL		-- Need ON
	]],
	[[	rlc-Config-v13xx					RLC-Config-v13xx		OPTIONAL		-- Need ON
	]]
}

DRB-ToAddModSCG-r12 ::=	SEQUENCE {
	drb-Identity-r12					DRB-Identity,
	drb-Type-r12						CHOICE {
		split-r12							NULL,
		scg-r12								SEQUENCE {
			eps-BearerIdentity-r12				INTEGER (0..15)	OPTIONAL,	-- Cond DRB-Setup
			pdcp-Config-r12						PDCP-Config		OPTIONAL	-- Cond PDCP-S
		}
	}															OPTIONAL,	-- Cond SetupS2
	rlc-ConfigSCG-r12					RLC-Config				OPTIONAL,	-- Cond SetupS
	rlc-Config-v1250						RLC-Config-v1250			OPTIONAL,	-- Need ON
	logicalChannelIdentitySCG-r12		INTEGER (3..10)			OPTIONAL,	-- Cond DRB-SetupS
	logicalChannelConfigSCG-r12			LogicalChannelConfig	OPTIONAL,	-- Cond SetupS
	...
}

DRB-ToReleaseList ::=				SEQUENCE (SIZE (1..maxDRB)) OF DRB-Identity

MeasSubframePatternPCell-r10 ::=		CHOICE {
	release								NULL,
	setup							MeasSubframePattern-r10
}

NeighCellsCRS-Info-r11 ::=		CHOICE {
	release							NULL,
	setup							CRS-AssistanceInfoList-r11
}

CRS-AssistanceInfoList-r11 ::=	SEQUENCE (SIZE (1..maxCellReport)) OF CRS-AssistanceInfo-r11

CRS-AssistanceInfo-r11 ::= SEQUENCE {
	physCellId-r11						PhysCellId,
	antennaPortsCount-r11				ENUMERATED {an1, an2, an4, spare1},
	mbsfn-SubframeConfigList-r11		MBSFN-SubframeConfigList,
	...
}

NeighCellsCRS-Info-r13 ::=		CHOICE {
	release							NULL,
	setup							CRS-AssistanceInfoList-r13
}

CRS-AssistanceInfoList-r13 ::=	SEQUENCE (SIZE (1..maxCellReport)) OF CRS-AssistanceInfo-r13

CRS-AssistanceInfo-r13 ::= SEQUENCE {
	physCellId-r13						PhysCellId,
	antennaPortsCount-r13				ENUMERATED {an1, an2, an4, spare1},
	mbsfn-SubframeConfigList-r13		MBSFN-SubframeConfigList	OPTIONAL,	-- Need ON
	...
}

NAICS-AssistanceInfo-r12 ::=		CHOICE {
	release							NULL,
	setup							SEQUENCE {
		neighCellsToReleaseList-r12		NeighCellsToReleaseList-r12			OPTIONAL	,	-- Need ON
		neighCellsToAddModList-r12		NeighCellsToAddModList-r12			OPTIONAL,	-- Need ON
		servCellp-a-r12					P-a	 							OPTIONAL	-- Need ON
	}
}

NeighCellsToReleaseList-r12 ::=	SEQUENCE (SIZE (1..maxNeighCell-r12)) OF PhysCellId

NeighCellsToAddModList-r12 ::=	SEQUENCE (SIZE (1..maxNeighCell-r12)) OF NeighCellsInfo-r12

NeighCellsInfo-r12	::=		SEQUENCE {
	physCellId-r12					PhysCellId,
	p-b-r12						INTEGER (0..3),
	crs-PortsCount-r12				ENUMERATED {n1, n2, n4, spare},
	mbsfn-SubframeConfig-r12		MBSFN-SubframeConfigList				OPTIONAL,	-- Need ON
	p-aList-r12					SEQUENCE (SIZE (1..maxP-a-PerNeighCell-r12)) OF P-a,
	transmissionModeList-r12		BIT STRING (SIZE(8)),
	resAllocGranularity-r12			INTEGER (1..4),
	...
}
P-a ::= ENUMERATED {	dB-6, dB-4dot77, dB-3, dB-1dot77,
									dB0, dB1, dB2, dB3}

-- ASN1STOP

RLC-Config ::=				CHOICE {
	am									SEQUENCE {
		ul-AM-RLC							UL-AM-RLC,
		dl-AM-RLC							DL-AM-RLC
	},
	um-Bi-Directional					SEQUENCE {
		ul-UM-RLC							UL-UM-RLC,
		dl-UM-RLC							DL-UM-RLC
	},
	um-Uni-Directional-UL				SEQUENCE {
		ul-UM-RLC							UL-UM-RLC
	},
	um-Uni-Directional-DL				SEQUENCE {
		dl-UM-RLC							DL-UM-RLC
	},
	...
}

RLC-Config-v1250 ::=				SEQUENCE {
	ul-extended-RLC-LI-Field-r12			BOOLEAN,
	dl-extended-RLC-LI-Field-r12			BOOLEAN
}

RLC-Config-v13xx ::=				SEQUENCE {
	ul-extended-RLC-AM-SN-r13 					BOOLEAN,
	dl-extended-RLC-AM-SN-r13 					BOOLEAN,
	pollPDU-v13xy								PollPDU-v13xy		OPTIONAL   -- Need OR
}

UL-AM-RLC ::=						SEQUENCE {
	t-PollRetransmit					T-PollRetransmit,
	pollPDU								PollPDU,
	pollByte							PollByte,
	maxRetxThreshold					ENUMERATED {
											t1, t2, t3, t4, t6, t8, t16, t32}
}

DL-AM-RLC ::=						SEQUENCE {
	t-Reordering						T-Reordering,
	t-StatusProhibit					T-StatusProhibit
}

UL-UM-RLC ::=						SEQUENCE {
	sn-FieldLength						SN-FieldLength
}

DL-UM-RLC ::=						SEQUENCE {
	sn-FieldLength						SN-FieldLength,
	t-Reordering						T-Reordering
}

SN-FieldLength ::=					ENUMERATED {size5, size10}

T-PollRetransmit ::=				ENUMERATED {
										ms5, ms10, ms15, ms20, ms25, ms30, ms35,
										ms40, ms45, ms50, ms55, ms60, ms65, ms70,
										ms75, ms80, ms85, ms90, ms95, ms100, ms105,
										ms110, ms115, ms120, ms125, ms130, ms135,
										ms140, ms145, ms150, ms155, ms160, ms165,
										ms170, ms175, ms180, ms185, ms190, ms195,
										ms200, ms205, ms210, ms215, ms220, ms225,
										ms230, ms235, ms240, ms245, ms250, ms300,
										ms350, ms400, ms450, ms500, spare9, spare8,
										spare7, spare6, spare5, spare4, spare3,
										spare2, spare1}

PollPDU ::=							ENUMERATED {
										p4, p8, p16, p32, p64, p128, p256, pInfinity}

PollPDU-v13xy ::=					ENUMERATED {
										p512, p1024, p2048, p4096, p6144, p8192, p12288, p16384}

PollByte ::=						ENUMERATED {
										kB25, kB50, kB75, kB100, kB125, kB250, kB375,
										kB500, kB750, kB1000, kB1250, kB1500, kB2000,
										kB3000, kBinfinity, spare1}

T-Reordering ::=					ENUMERATED {
										ms0, ms5, ms10, ms15, ms20, ms25, ms30, ms35,
										ms40, ms45, ms50, ms55, ms60, ms65, ms70,
										ms75, ms80, ms85, ms90, ms95, ms100, ms110,
										ms120, ms130, ms140, ms150, ms160, ms170,
										ms180, ms190, ms200, spare1}

T-StatusProhibit ::=				ENUMERATED {
										ms0, ms5, ms10, ms15, ms20, ms25, ms30, ms35,
										ms40, ms45, ms50, ms55, ms60, ms65, ms70,
										ms75, ms80, ms85, ms90, ms95, ms100, ms105,
										ms110, ms115, ms120, ms125, ms130, ms135,
										ms140, ms145, ms150, ms155, ms160, ms165,
										ms170, ms175, ms180, ms185, ms190, ms195,
										ms200, ms205, ms210, ms215, ms220, ms225,
										ms230, ms235, ms240, ms245, ms250, ms300,
										ms350, ms400, ms450, ms500, spare8, spare7,
										spare6, spare5, spare4, spare3, spare2,
										spare1}

-- ASN1STOP

RLF-TimersAndConstants-r9 ::=			CHOICE {
	release									NULL,
	setup									SEQUENCE {
		t301-r9								ENUMERATED {
												ms100, ms200, ms300, ms400, ms600, ms1000, ms1500,
												ms2000},
		t310-r9								ENUMERATED {
												ms0, ms50, ms100, ms200, ms500, ms1000, ms2000},
		n310-r9								ENUMERATED {
												n1, n2, n3, n4, n6, n8, n10, n20},
		t311-r9								ENUMERATED {
												ms1000, ms3000, ms5000, ms10000, ms15000,
												ms20000, ms30000},
		n311-r9								ENUMERATED {
												n1, n2, n3, n4, n5, n6, n8, n10},
		...
	}
}

RLF-TimersAndConstantsSCG-r12 ::=			CHOICE {
	release								NULL,
	setup								SEQUENCE {
		t313-r12							ENUMERATED {
												ms0, ms50, ms100, ms200, ms500, ms1000, ms2000},
		n313-r12							ENUMERATED {
												n1, n2, n3, n4, n6, n8, n10, n20},
		n314-r12							ENUMERATED {
												n1, n2, n3, n4, n5, n6, n8, n10},
		...
	}
}

-- ASN1STOP

RN-SubframeConfig-r10 ::=		SEQUENCE {
	subframeConfigPattern-r10			CHOICE {
		subframeConfigPatternFDD-r10	BIT STRING (SIZE(8)),
		subframeConfigPatternTDD-r10	INTEGER (0..31)
	}																	OPTIONAL,	-- Need ON
	rpdcch-Config-r10				SEQUENCE {
		resourceAllocationType-r10		ENUMERATED {type0, type1, type2Localized, type2Distributed,
													spare4, spare3, spare2, spare1},
		resourceBlockAssignment-r10			CHOICE {
			type01-r10							CHOICE {
				nrb6-r10							BIT STRING (SIZE(6)),
				nrb15-r10							BIT STRING (SIZE(8)),
				nrb25-r10							BIT STRING (SIZE(13)),
				nrb50-r10							BIT STRING (SIZE(17)),
				nrb75-r10							BIT STRING (SIZE(19)),
				nrb100-r10							BIT STRING (SIZE(25))
			},
			type2-r10							CHOICE {
				nrb6-r10							BIT STRING (SIZE(5)),
				nrb15-r10							BIT STRING (SIZE(7)),
				nrb25-r10							BIT STRING (SIZE(9)),
				nrb50-r10							BIT STRING (SIZE(11)),
				nrb75-r10							BIT STRING (SIZE(12)),
				nrb100-r10							BIT STRING (SIZE(13))
			},
			...
		},
		demodulationRS-r10				CHOICE {
			interleaving-r10				ENUMERATED {crs},
			noInterleaving-r10				ENUMERATED {crs, dmrs}
		},
		pdsch-Start-r10					INTEGER (1..3),
		pucch-Config-r10				CHOICE {
			tdd								CHOICE {
				channelSelectionMultiplexingBundling	SEQUENCE {
					n1PUCCH-AN-List-r10			SEQUENCE (SIZE (1..4)) OF INTEGER (0..2047)
				},
				fallbackForFormat3				SEQUENCE {
					n1PUCCH-AN-P0-r10				INTEGER (0..2047),
					n1PUCCH-AN-P1-r10				INTEGER (0..2047)		OPTIONAL	-- Need OR
				}
			},
			fdd								SEQUENCE {
				n1PUCCH-AN-P0-r10				INTEGER (0..2047),
				n1PUCCH-AN-P1-r10				INTEGER (0..2047)			OPTIONAL	-- Need OR
			}
		},
		...
	}																	OPTIONAL,	-- Need ON
	...
}

-- ASN1STOP

SchedulingRequestConfig ::=		CHOICE {
	release								NULL,
	setup								SEQUENCE {
		sr-PUCCH-ResourceIndex				INTEGER (0..2047),
		sr-ConfigIndex						INTEGER (0..157),
		dsr-TransMax						ENUMERATED {
												n4, n8, n16, n32, n64, spare3, spare2, spare1}
	}
}

SchedulingRequestConfig-v1020 ::=	SEQUENCE {
	sr-PUCCH-ResourceIndexP1-r10		INTEGER (0..2047)			OPTIONAL		-- Need OR
}

-- ASN1STOP

SoundingRS-UL-ConfigCommon ::=		CHOICE {
	release								NULL,
	setup								SEQUENCE {
		srs-BandwidthConfig					ENUMERATED {bw0, bw1, bw2, bw3, bw4, bw5, bw6, bw7},
		srs-SubframeConfig					ENUMERATED {
												sc0, sc1, sc2, sc3, sc4, sc5, sc6, sc7,
												sc8, sc9, sc10, sc11, sc12, sc13, sc14, sc15},
		ackNackSRS-SimultaneousTransmission	BOOLEAN,
		srs-MaxUpPts						ENUMERATED {true}			OPTIONAL	-- Cond TDD
	}
}

SoundingRS-UL-ConfigDedicated ::=	CHOICE{
	release								NULL,
	setup								SEQUENCE {
		srs-Bandwidth						ENUMERATED {bw0, bw1, bw2, bw3},
		srs-HoppingBandwidth				ENUMERATED {hbw0, hbw1, hbw2, hbw3},
		freqDomainPosition					INTEGER (0..23),
		duration							BOOLEAN,
		srs-ConfigIndex						INTEGER (0..1023),
		transmissionComb					INTEGER (0..1),
		cyclicShift							ENUMERATED {cs0, cs1, cs2, cs3, cs4, cs5, cs6, cs7}
	}
}

SoundingRS-UL-ConfigDedicated-v1020 ::=	SEQUENCE {
	srs-AntennaPort-r10					SRS-AntennaPort
}

SoundingRS-UL-ConfigDedicated-v13x0 ::=	CHOICE{
	release								NULL,
	setup								SEQUENCE {
		transmissionComb-v13x0				INTEGER (2..3)				OPTIONAL,	-- Need OR
		cyclicShift-v13x0					ENUMERATED {cs8, cs9, cs10, cs11}	OPTIONAL,	-- Need OR
		transmissionCombNum-r13				ENUMERATED {n2, n4}		OPTIONAL	-- Need OR
	}
}

SoundingRS-UL-ConfigDedicatedUpPTsExt-r13 ::=	CHOICE{
	release								NULL,
	setup								SEQUENCE {
		srs-UpPtsAdd						ENUMERATED {sym2, sym4},
		srs-Bandwidth-r13					ENUMERATED {bw0, bw1, bw2, bw3},
		srs-HoppingBandwidth-r13			ENUMERATED {hbw0, hbw1, hbw2, hbw3},
		freqDomainPosition-r13				INTEGER (0..23),
		duration-r13						BOOLEAN,
		srs-ConfigIndex-r13					INTEGER (0..1023),
		transmissionComb-r13				INTEGER (0..3),
		cyclicShift-r13						ENUMERATED {cs0, cs1, cs2, cs3, cs4, cs5, cs6, cs7,
														cs8, cs9, cs10, cs11},
		srs-AntennaPort-r13					SRS-AntennaPort,
		transmissionCombNum-r13				ENUMERATED {n2, n4}
	}
}

SoundingRS-UL-ConfigDedicatedAperiodic-r10 ::=	CHOICE{
	release								NULL,
	setup								SEQUENCE {
		srs-ConfigIndexAp-r10				INTEGER (0..31),
		srs-ConfigApDCI-Format4-r10			SEQUENCE (SIZE (1..3)) OF SRS-ConfigAp-r10	OPTIONAL,--Need ON
		srs-ActivateAp-r10					CHOICE {
				release							NULL,
				setup							SEQUENCE {
					srs-ConfigApDCI-Format0-r10			SRS-ConfigAp-r10,
					srs-ConfigApDCI-Format1a2b2c-r10		SRS-ConfigAp-r10,
					...
				}
		}																	OPTIONAL	-- Need ON
	}
}

SoundingRS-UL-ConfigDedicatedAperiodic-v13x0 ::=	CHOICE{
	release								NULL,
	setup								SEQUENCE {
		srs-ConfigApDCI-Format4-v13x0		SEQUENCE (SIZE (1..3)) OF SRS-ConfigAp-v13x0	OPTIONAL,--Need ON
		srs-ActivateAp-v13x0				CHOICE {
				release							NULL,
				setup							SEQUENCE {
					srs-ConfigApDCI-Format0-v13x0		SRS-ConfigAp-v13x0	OPTIONAL,	-- Need ON
					srs-ConfigApDCI-Format1a2b2c-v13x0	SRS-ConfigAp-v13x0	OPTIONAL,	-- Need ON
					...
				}
		}																	OPTIONAL	-- Need ON
	}
}

SoundingRS-UL-ConfigDedicatedAperiodicUpPTsExt-r13 ::=	CHOICE{
	release								NULL,
	setup								SEQUENCE {
		srs-UpPtsAdd						ENUMERATED {sym2, sym4},
		srs-ConfigIndexAp-r13				INTEGER (0..31),
		srs-ConfigApDCI-Format4-r13			SEQUENCE (SIZE (1..3)) OF SRS-ConfigAp-r13	OPTIONAL,--Need ON
		srs-ActivateAp-r13					CHOICE {
				release							NULL,
				setup							SEQUENCE {
					srs-ConfigApDCI-Format0-r13			SRS-ConfigAp-r13,
					srs-ConfigApDCI-Format1a2b2c-r13		SRS-ConfigAp-r13,
					...
				}
		}																	OPTIONAL	-- Need ON
	}
}

SRS-ConfigAp-r10 ::= SEQUENCE {
	srs-AntennaPortAp-r10				SRS-AntennaPort,
	srs-BandwidthAp-r10					ENUMERATED {bw0, bw1, bw2, bw3},
	freqDomainPositionAp-r10			INTEGER (0..23),
	transmissionCombAp-r10				INTEGER (0..1),
	cyclicShiftAp-r10					ENUMERATED {cs0, cs1, cs2, cs3, cs4, cs5, cs6, cs7}
}

SRS-ConfigAp-v13x0 ::= SEQUENCE {
	transmissionCombAp-v13x0			INTEGER (2..3)						OPTIONAL,	-- Need OR
	cyclicShiftAp-v13x0					ENUMERATED {cs8, cs9, cs10, cs11}	OPTIONAL,	-- Need OR
	transmissionCombNum-r13				ENUMERATED {n2, n4}			OPTIONAL	-- Need OR
}

SRS-ConfigAp-r13 ::= SEQUENCE {
	srs-AntennaPortAp-r10				SRS-AntennaPort,
	srs-BandwidthAp-r10					ENUMERATED {bw0, bw1, bw2, bw3},
	freqDomainPositionAp-r10			INTEGER (0..23),
	transmissionCombAp-r10				INTEGER (0..3),
	cyclicShiftAp-r10					ENUMERATED {cs0, cs1, cs2, cs3, cs4, cs5, cs6, cs7,
											cs8, cs9, cs10, cs11},
	transmissionCombNum-r13				ENUMERATED {n2, n4}
}

SRS-AntennaPort ::=					ENUMERATED {an1, an2, an4, spare1}

-- ASN1STOP

SPS-Config ::=	SEQUENCE {
	semiPersistSchedC-RNTI			C-RNTI					OPTIONAL,			-- Need OR
	sps-ConfigDL					SPS-ConfigDL			OPTIONAL,			-- Need ON
	sps-ConfigUL					SPS-ConfigUL			OPTIONAL			-- Need ON
}

SPS-ConfigDL ::=	CHOICE{
	release							NULL,
	setup							SEQUENCE {
		semiPersistSchedIntervalDL			ENUMERATED {
												sf10, sf20, sf32, sf40, sf64, sf80,
												sf128, sf160, sf320, sf640, spare6,
												spare5, spare4, spare3, spare2,
												spare1},
		numberOfConfSPS-Processes			INTEGER (1..8),
		n1PUCCH-AN-PersistentList			N1PUCCH-AN-PersistentList,
	--	...,
		[[	twoAntennaPortActivated-r10		CHOICE {
				release							NULL,
				setup							SEQUENCE {
					n1PUCCH-AN-PersistentListP1-r10	N1PUCCH-AN-PersistentList
				}
			}																OPTIONAL	-- Need ON
		]]
	}
}

SPS-ConfigUL ::=	CHOICE {
	release							NULL,
	setup							SEQUENCE {
		semiPersistSchedIntervalUL			ENUMERATED {
												sf10, sf20, sf32, sf40, sf64, sf80,
												sf128, sf160, sf320, sf640, spare6,
												spare5, spare4, spare3, spare2,
												spare1},
		implicitReleaseAfter				ENUMERATED {e2, e3, e4, e8},
		p0-Persistent						SEQUENCE {
			p0-NominalPUSCH-Persistent			INTEGER (-126..24),
			p0-UE-PUSCH-Persistent				INTEGER (-8..7)
		}		OPTIONAL,												-- Need OP
		twoIntervalsConfig					ENUMERATED {true}			OPTIONAL,	-- Cond TDD
	--	...,
		[[	p0-PersistentSubframeSet2-r12		CHOICE {
				release								NULL,
				setup								SEQUENCE {
					p0-NominalPUSCH-PersistentSubframeSet2-r12			INTEGER (-126..24),
					p0-UE-PUSCH-PersistentSubframeSet2-r12				INTEGER (-8..7)
				}
			} 															OPTIONAL	-- Need ON
		]]
	}
}

N1PUCCH-AN-PersistentList ::=		SEQUENCE (SIZE (1..4)) OF INTEGER (0..2047)

-- ASN1STOP

TDD-Config ::=						SEQUENCE {
	subframeAssignment					ENUMERATED {
											sa0, sa1, sa2, sa3, sa4, sa5, sa6},
	specialSubframePatterns				ENUMERATED {
											ssp0, ssp1, ssp2, ssp3, ssp4,ssp5, ssp6, ssp7,
											ssp8}
}

TDD-Config-v1130 ::=				SEQUENCE {
	specialSubframePatterns-v1130		ENUMERATED {ssp7,ssp9}
}

TDD-ConfigSL-r12 ::=		SEQUENCE {
	subframeAssignmentSL-r12				ENUMERATED {
											none, sa0, sa1, sa2, sa3, sa4, sa5, sa6}
}

-- ASN1STOP

TimeAlignmentTimer ::=					ENUMERATED {
												sf500, sf750, sf1280, sf1920, sf2560, sf5120,
												sf10240, infinity}
-- ASN1STOP

TPC-PDCCH-Config ::=					CHOICE {
	release								NULL,
	setup								SEQUENCE {
		tpc-RNTI							BIT STRING (SIZE (16)),
		tpc-Index							TPC-Index
	}
}

TPC-PDCCH-ConfigSCell ::=					CHOICE {
	release								NULL,
	setup								SEQUENCE {
		tpc-Index-PUCCH-SCell-r13		TPC-Index
	}
}

TPC-Index ::=							CHOICE {
	indexOfFormat3							INTEGER (1..15),
	indexOfFormat3A							INTEGER (1..31)
}

-- ASN1STOP

UplinkPowerControlCommon ::=		SEQUENCE {
	p0-NominalPUSCH						INTEGER (-126..24),
	alpha								Alpha-r12,
	p0-NominalPUCCH						INTEGER (-127..-96),
	deltaFList-PUCCH					DeltaFList-PUCCH,
	deltaPreambleMsg3					INTEGER (-1..6)
}

UplinkPowerControlCommon-v1020 ::=	SEQUENCE {
	deltaF-PUCCH-Format3-r10				ENUMERATED {deltaF-1, deltaF0, deltaF1, deltaF2,
														deltaF3, deltaF4, deltaF5, deltaF6},
	deltaF-PUCCH-Format1bCS-r10				ENUMERATED {deltaF1, deltaF2, spare2, spare1}
}

UplinkPowerControlCommon-v13xy ::=	SEQUENCE {
	deltaF-PUCCH-Format4				ENUMERATED {deltaFX, deltaFX1, deltaFX2,deltaFX3, deltaFX4, deltaFX5, deltaFX6, deltaFX7}		OPTIONAL,		-- Need OR
	deltaF-PUCCH-Format5				ENUMERATED { deltaFX, deltaFX1, deltaFX2, deltaFX3, deltaFX4, deltaFX5, deltaFX6, deltaFX7}		OPTIONAL			-- Need OR
}

UplinkPowerControlCommonPSCell-r12 ::=		SEQUENCE {
-- For uplink power control the additional/ missing fields are signalled (compared to SCell)
	deltaF-PUCCH-Format3-r12				ENUMERATED {deltaF-1, deltaF0, deltaF1, deltaF2,
														deltaF3, deltaF4, deltaF5, deltaF6},
	deltaF-PUCCH-Format1bCS-r12				ENUMERATED {deltaF1, deltaF2, spare2, spare1},
	p0-NominalPUCCH-r12						INTEGER (-127..-96),
	deltaFList-PUCCH-r12					DeltaFList-PUCCH
}

UplinkPowerControlCommonPSCell-v13xy ::=		SEQUENCE {
-- For uplink power control the additional/ missing fields are signalled (compared to SCell)
	deltaF-PUCCH-Format4				ENUMERATED {deltaFX, deltaFX1, deltaFX2,deltaFX3, deltaFX4, deltaFX5, deltaFX6, deltaFX7}		OPTIONAL,		-- Need OR
	deltaF-PUCCH-Format5				ENUMERATED { deltaFX, deltaFX1, deltaFX2,deltaFX3, deltaFX4, deltaFX5, deltaFX6, deltaFX7}		OPTIONAL		-- Need OR
}

UplinkPowerControlCommonSCell-r10 ::=	SEQUENCE {
	p0-NominalPUSCH-r10					INTEGER (-126..24),
	alpha-r10							Alpha-r12
}

UplinkPowerControlCommonSCell-v1130 ::=	SEQUENCE {
	deltaPreambleMsg3-r11				INTEGER (-1..6)
}

UplinkPowerControlDedicated ::=		SEQUENCE {
	p0-UE-PUSCH							INTEGER (-8..7),
	deltaMCS-Enabled					ENUMERATED {en0, en1},
	accumulationEnabled					BOOLEAN,
	p0-UE-PUCCH							INTEGER (-8..7),
	pSRS-Offset							INTEGER (0..15),
	filterCoefficient					FilterCoefficient					DEFAULT fc4
}

UplinkPowerControlDedicated-v1020 ::= SEQUENCE {
	deltaTxD-OffsetListPUCCH-r10		DeltaTxD-OffsetListPUCCH-r10	OPTIONAL,		-- Need OR
	pSRS-OffsetAp-r10					INTEGER (0..15)					OPTIONAL		-- Need OR
}

UplinkPowerControlDedicated-v1130 ::=		SEQUENCE {
	pSRS-Offset-v1130						INTEGER (16..31)			OPTIONAL,		-- Need OR
	pSRS-OffsetAp-v1130						INTEGER (16..31)			OPTIONAL,		-- Need OR
	deltaTxD-OffsetListPUCCH-v1130			DeltaTxD-OffsetListPUCCH-v1130	OPTIONAL	-- Need OR
}

UplinkPowerControlDedicated-v1250 ::=	SEQUENCE {
	set2PowerControlParameter		CHOICE {
		release							NULL,
		setup							SEQUENCE {
			tpc-SubframeSet-r12					BIT STRING (SIZE(10)),
			p0-NominalPUSCH-SubframeSet2-r12		INTEGER (-126..24),
			alpha-SubframeSet2-r12				Alpha-r12,
			p0-UE-PUSCH-SubframeSet2-r12			INTEGER (-8..7)
		}
	}
}

UplinkPowerControlDedicatedSCell-r10 ::=		SEQUENCE {
	p0-UE-PUSCH-r10						INTEGER (-8..7),
	deltaMCS-Enabled-r10					ENUMERATED {en0, en1},
	accumulationEnabled-r10				BOOLEAN,
	pSRS-Offset-r10						INTEGER (0..15),
	pSRS-OffsetAp-r10					INTEGER (0..15) 					OPTIONAL,	-- Need OR
	filterCoefficient-r10				FilterCoefficient					DEFAULT fc4,
	pathlossReferenceLinking-r10		ENUMERATED {pCell, sCell}
}

Alpha-r12 ::=						ENUMERATED {al0, al04, al05, al06, al07, al08, al09, al1}

DeltaFList-PUCCH ::=				SEQUENCE {
	deltaF-PUCCH-Format1				ENUMERATED {deltaF-2, deltaF0, deltaF2},
	deltaF-PUCCH-Format1b				ENUMERATED {deltaF1, deltaF3, deltaF5},
	deltaF-PUCCH-Format2				ENUMERATED {deltaF-2, deltaF0, deltaF1, deltaF2},
	deltaF-PUCCH-Format2a				ENUMERATED {deltaF-2, deltaF0, deltaF2},
	deltaF-PUCCH-Format2b				ENUMERATED {deltaF-2, deltaF0, deltaF2}
}

DeltaTxD-OffsetListPUCCH-r10 ::=	SEQUENCE {
	deltaTxD-OffsetPUCCH-Format1-r10		ENUMERATED {dB0, dB-2},
	deltaTxD-OffsetPUCCH-Format1a1b-r10		ENUMERATED {dB0, dB-2},
	deltaTxD-OffsetPUCCH-Format22a2b-r10	ENUMERATED {dB0, dB-2},
	deltaTxD-OffsetPUCCH-Format3-r10		ENUMERATED {dB0, dB-2},
	...

}

DeltaTxD-OffsetListPUCCH-v1130 ::=	SEQUENCE {
	deltaTxD-OffsetPUCCH-Format1bCS-r11		ENUMERATED {dB0, dB-1}
}
-- ASN1STOP

NextHopChainingCount ::=					INTEGER (0..7)

-- ASN1STOP

SecurityAlgorithmConfig ::=			SEQUENCE {
	cipheringAlgorithm					CipheringAlgorithm-r12,
	integrityProtAlgorithm				ENUMERATED {
											eia0-v920, eia1, eia2, eia3-v1130, spare4, spare3,
											spare2, spare1, ...}
}

CipheringAlgorithm-r12 ::=				ENUMERATED {
											eea0, eea1, eea2, eea3-v1130, spare4, spare3,
											spare2, spare1, ...}

-- ASN1STOP

ShortMAC-I ::=						BIT STRING (SIZE (16))

-- ASN1STOP

AdditionalSpectrumEmission ::=		INTEGER (1..32)

-- ASN1STOP

ARFCN-ValueCDMA2000 ::=			INTEGER (0..2047)

-- ASN1STOP

ARFCN-ValueEUTRA ::=				INTEGER (0..maxEARFCN)

ARFCN-ValueEUTRA-v9e0 ::=			INTEGER (maxEARFCN-Plus1..maxEARFCN2)

ARFCN-ValueEUTRA-r9 ::=				INTEGER (0..maxEARFCN2)

-- ASN1STOP

ARFCN-ValueGERAN ::=			INTEGER (0..1023)

-- ASN1STOP

ARFCN-ValueUTRA ::=					INTEGER (0..16383)

-- ASN1STOP

BandclassCDMA2000 ::=					ENUMERATED {
											bc0, bc1, bc2, bc3, bc4, bc5, bc6, bc7, bc8,
											bc9, bc10, bc11, bc12, bc13, bc14, bc15, bc16,
											bc17, bc18-v9a0, bc19-v9a0, bc20-v9a0, bc21-v9a0,
											spare10, spare9, spare8, spare7, spare6, spare5, spare4,
											spare3, spare2, spare1, ...}

-- ASN1STOP

BandIndicatorGERAN ::=			ENUMERATED {dcs1800, pcs1900}

-- ASN1STOP

CarrierFreqCDMA2000 ::=			SEQUENCE {
	bandClass							BandclassCDMA2000,
	arfcn							ARFCN-ValueCDMA2000
}

-- ASN1STOP

CarrierFreqGERAN ::=			SEQUENCE {
	arfcn							ARFCN-ValueGERAN,
	bandIndicator					BandIndicatorGERAN
}

-- ASN1STOP

CarrierFreqsGERAN ::=			SEQUENCE {
	startingARFCN						ARFCN-ValueGERAN,
	bandIndicator						BandIndicatorGERAN,
	followingARFCNs						CHOICE {
		explicitListOfARFCNs				ExplicitListOfARFCNs,
		equallySpacedARFCNs					SEQUENCE {
			arfcn-Spacing						INTEGER (1..8),
			numberOfFollowingARFCNs				INTEGER (0..31)
		},
		variableBitMapOfARFCNs				OCTET STRING (SIZE (1..16))
	}
}

ExplicitListOfARFCNs ::=			SEQUENCE (SIZE (0..31)) OF ARFCN-ValueGERAN

-- ASN1STOP

CarrierFreqListMBMS-r11 ::=		SEQUENCE (SIZE (1..maxFreqMBMS-r11)) OF ARFCN-ValueEUTRA-r9

-- ASN1STOP

CDMA2000-Type ::=					ENUMERATED {type1XRTT, typeHRPD}

-- ASN1STOP

CellIdentity ::=					BIT STRING (SIZE (28))

-- ASN1STOP

CellIndexList ::=						SEQUENCE (SIZE (1..maxCellMeas)) OF CellIndex

CellIndex ::=							INTEGER (1..maxCellMeas)

-- ASN1STOP

CellReselectionPriority ::=				INTEGER (0..7)

-- ASN1STOP

CellReselectionSubPriority-r13 ::=			ENUMERATED {oDot2, oDot4, oDot6, oDot8}

-- ASN1STOP

CSFB-RegistrationParam1XRTT ::=		SEQUENCE {
	sid									BIT STRING (SIZE (15)),
	nid									BIT STRING (SIZE (16)),
	multipleSID							BOOLEAN,
	multipleNID							BOOLEAN,
	homeReg								BOOLEAN,
	foreignSIDReg						BOOLEAN,
	foreignNIDReg						BOOLEAN,
	parameterReg						BOOLEAN,
	powerUpReg							BOOLEAN,
	registrationPeriod					BIT STRING (SIZE (7)),
	registrationZone					BIT STRING (SIZE (12)),
	totalZone							BIT STRING (SIZE (3)),
	zoneTimer							BIT STRING (SIZE (3))
}

CSFB-RegistrationParam1XRTT-v920 ::=	SEQUENCE {
	powerDownReg-r9						ENUMERATED {true}
}

-- ASN1STOP

CellGlobalIdEUTRA ::=					SEQUENCE {
	plmn-Identity							PLMN-Identity,
	cellIdentity							CellIdentity
}

-- ASN1STOP

CellGlobalIdUTRA ::=					SEQUENCE {
	plmn-Identity							PLMN-Identity,
	cellIdentity							BIT STRING (SIZE (28))
}

-- ASN1STOP

CellGlobalIdGERAN ::=					SEQUENCE {
	plmn-Identity							PLMN-Identity,
	locationAreaCode						BIT STRING (SIZE (16)),
	cellIdentity						BIT STRING (SIZE (16))
}

-- ASN1STOP

CellGlobalIdCDMA2000 ::=				CHOICE {
	cellGlobalId1XRTT						BIT STRING (SIZE (47)),
	cellGlobalIdHRPD						BIT STRING (SIZE (128))
}

-- ASN1STOP

CSG-Identity ::=					BIT STRING (SIZE (27))

-- ASN1STOP

FreqBandIndicator ::=					INTEGER (1..maxFBI)

FreqBandIndicator-v9e0 ::=				INTEGER (maxFBI-Plus1..maxFBI2)

FreqBandIndicator-r11 ::=				INTEGER (1..maxFBI2)

-- ASN1STOP

MobilityControlInfo ::=		SEQUENCE {
	targetPhysCellId					PhysCellId,
	carrierFreq							CarrierFreqEUTRA					OPTIONAL,	-- Cond HO-toEUTRA2
	carrierBandwidth					CarrierBandwidthEUTRA				OPTIONAL,	-- Cond HO-toEUTRA
	additionalSpectrumEmission			AdditionalSpectrumEmission			OPTIONAL,	-- Cond HO-toEUTRA
	t304								ENUMERATED {
											ms50, ms100, ms150, ms200, ms500, ms1000,
											ms2000, spare1},
	newUE-Identity						C-RNTI,
	radioResourceConfigCommon			RadioResourceConfigCommon,
	rach-ConfigDedicated				RACH-ConfigDedicated				OPTIONAL,	-- Need OP
--	...,
	[[	carrierFreq-v9e0				CarrierFreqEUTRA-v9e0				OPTIONAL	-- Need ON
	]],
	[[	drb-ContinueROHC-r11			ENUMERATED {true}					OPTIONAL	-- Cond HO
	]]
}

MobilityControlInfoSCG-r12 ::=		SEQUENCE {
	t307-r12							ENUMERATED {
											ms50, ms100, ms150, ms200, ms500, ms1000,
											ms2000, spare1},
	ue-IdentitySCG-r12					C-RNTI							OPTIONAL,	-- Cond SCGEst,
	rach-ConfigDedicated-r12			RACH-ConfigDedicated			OPTIONAL,	-- Need OP
	cipheringAlgorithmSCG-r12		CipheringAlgorithm-r12		OPTIONAL,	-- Need ON
	...
}

CarrierBandwidthEUTRA ::=			SEQUENCE {
	dl-Bandwidth						ENUMERATED {
												n6, n15, n25, n50, n75, n100, spare10,
												spare9, spare8, spare7, spare6, spare5,
												spare4, spare3, spare2, spare1},
	ul-Bandwidth						ENUMERATED {
												n6, n15, n25, n50, n75, n100, spare10,
												spare9, spare8, spare7, spare6, spare5,
												spare4, spare3, spare2, spare1}	OPTIONAL -- Need OP
}

CarrierFreqEUTRA ::=				SEQUENCE {
	dl-CarrierFreq						ARFCN-ValueEUTRA,
	ul-CarrierFreq						ARFCN-ValueEUTRA				OPTIONAL	-- Cond FDD
}

CarrierFreqEUTRA-v9e0 ::=			SEQUENCE {
	dl-CarrierFreq-v9e0					ARFCN-ValueEUTRA-r9,
	ul-CarrierFreq-v9e0					ARFCN-ValueEUTRA-r9			OPTIONAL	-- Cond FDD
}

-- ASN1STOP

MobilityParametersCDMA2000 ::=			OCTET STRING

-- ASN1STOP

MobilityStateParameters ::=			SEQUENCE {
	t-Evaluation						ENUMERATED {
											s30, s60, s120, s180, s240, spare3, spare2, spare1},
	t-HystNormal						ENUMERATED {
											s30, s60, s120, s180, s240, spare3, spare2, spare1},
	n-CellChangeMedium					INTEGER (1..16),
	n-CellChangeHigh					INTEGER (1..16)
}

-- ASN1STOP

MultiBandInfoList ::=	SEQUENCE (SIZE (1..maxMultiBands)) OF FreqBandIndicator

MultiBandInfoList-v9e0 ::=	SEQUENCE (SIZE (1..maxMultiBands)) OF MultiBandInfo-v9e0

MultiBandInfoList-v10j0 ::=	SEQUENCE (SIZE (1..maxMultiBands)) OF NS-PmaxList-r10

MultiBandInfoList-r11 ::=	SEQUENCE (SIZE (1..maxMultiBands)) OF FreqBandIndicator-r11

MultiBandInfo-v9e0 ::=		SEQUENCE {
	freqBandIndicator-v9e0				FreqBandIndicator-v9e0		OPTIONAL	-- Need OP
}

-- ASN1STOP

NS-PmaxList-r10 ::=				SEQUENCE (SIZE (1..maxNS-Pmax-r10)) OF NS-PmaxValue-r10

NS-PmaxValue-r10 ::=			SEQUENCE {
	additionalPmax-r10					P-Max							OPTIONAL,	-- Need OP
	additionalSpectrumEmission			AdditionalSpectrumEmission
}

-- ASN1STOP

PhysCellId ::=						INTEGER (0..503)

-- ASN1STOP

PhysCellIdRange ::=				SEQUENCE {
	start							PhysCellId,
	range							ENUMERATED {
										n4, n8, n12, n16, n24, n32, n48, n64, n84,
										n96, n128, n168, n252, n504, spare2,
										spare1} 					OPTIONAL	-- Need OP
}

-- ASN1STOP

PhysCellIdRangeUTRA-FDDList-r9::=		SEQUENCE (SIZE (1..maxPhysCellIdRange-r9)) OF PhysCellIdRangeUTRA-FDD-r9

PhysCellIdRangeUTRA-FDD-r9 ::=			SEQUENCE {
		start-r9							PhysCellIdUTRA-FDD,
		range-r9							INTEGER (2..512)				OPTIONAL	-- Need OP
}

-- ASN1STOP

PhysCellIdCDMA2000 ::=			INTEGER (0..maxPNOffset)

-- ASN1STOP

PhysCellIdGERAN ::=				SEQUENCE {
	networkColourCode					BIT STRING (SIZE (3)),
	baseStationColourCode				BIT STRING (SIZE (3))
}

-- ASN1STOP

PhysCellIdUTRA-FDD ::=				INTEGER (0..511)

-- ASN1STOP

PhysCellIdUTRA-TDD ::=				INTEGER (0..127)

-- ASN1STOP

PLMN-Identity ::=					SEQUENCE {
	mcc									MCC					OPTIONAL,					-- Cond MCC
	mnc									MNC
}

MCC ::=								SEQUENCE (SIZE (3)) OF
											MCC-MNC-Digit

MNC ::=								SEQUENCE (SIZE (2..3)) OF
											MCC-MNC-Digit

MCC-MNC-Digit ::=					INTEGER (0..9)


-- ASN1STOP

PLMN-IdentityList3-r11 ::=				SEQUENCE (SIZE (1..16)) OF PLMN-Identity

-- ASN1STOP

PreRegistrationInfoHRPD ::=			SEQUENCE {
	preRegistrationAllowed				BOOLEAN,
	preRegistrationZoneId				PreRegistrationZoneIdHRPD	OPTIONAL, -- cond PreRegAllowed
	secondaryPreRegistrationZoneIdList	SecondaryPreRegistrationZoneIdListHRPD	OPTIONAL -- Need OR
}

SecondaryPreRegistrationZoneIdListHRPD ::=	SEQUENCE (SIZE (1..2)) OF PreRegistrationZoneIdHRPD

PreRegistrationZoneIdHRPD ::=			INTEGER (0..255)

-- ASN1STOP

Q-QualMin-r9 ::=					INTEGER (-34..-3)

-- ASN1STOP

Q-RxLevMin ::=						INTEGER (-70..-22)

-- ASN1STOP

Q-OffsetRange ::=						ENUMERATED {
												dB-24, dB-22, dB-20, dB-18, dB-16, dB-14,
												dB-12, dB-10, dB-8, dB-6, dB-5, dB-4, dB-3,
												dB-2, dB-1, dB0, dB1, dB2, dB3, dB4, dB5,
												dB6, dB8, dB10, dB12, dB14, dB16, dB18,
												dB20, dB22, dB24}

-- ASN1STOP

Q-OffsetRangeInterRAT ::=					INTEGER (-15..15)

-- ASN1STOP

ReselectionThreshold ::=				INTEGER (0..31)

-- ASN1STOP

ReselectionThresholdQ-r9 ::=			INTEGER (0..31)

-- ASN1STOP

SCellIndex-r10 ::=						INTEGER (1..7)
SCellIndex-v13xy ::=					INTEGER (8..31)
SCellIndex-r13 ::=						INTEGER (1..31)

-- ASN1STOP

ServCellIndex-r10 ::=					INTEGER (0..7)
ServCellIndex-v13xy ::=					INTEGER (8..31)
ServCellIndexFull-r13 ::=				INTEGER (0..31)

-- ASN1STOP

SpeedStateScaleFactors ::=			SEQUENCE {
	sf-Medium							ENUMERATED {oDot25, oDot5, oDot75, lDot0},
	sf-High								ENUMERATED {oDot25, oDot5, oDot75, lDot0}
}
-- ASN1STOP

SystemInfoListGERAN ::=				SEQUENCE (SIZE (1..maxGERAN-SI)) OF
										OCTET STRING (SIZE (1..23))

-- ASN1STOP

SystemTimeInfoCDMA2000 ::=			SEQUENCE {
	cdma-EUTRA-Synchronisation			BOOLEAN,
	cdma-SystemTime						CHOICE {
		synchronousSystemTime				BIT STRING (SIZE (39)),
		asynchronousSystemTime				BIT STRING (SIZE (49))
	}
}

-- ASN1STOP

TrackingAreaCode ::=				BIT STRING (SIZE (16))

-- ASN1STOP

T-Reselection ::=					INTEGER (0..7)

-- ASN1STOP

AllowedMeasBandwidth ::=				ENUMERATED {mbw6, mbw15, mbw25, mbw50, mbw75, mbw100}

-- ASN1STOP

CSI-RSRP-Range-r12 ::=						INTEGER(0..97)

-- ASN1STOP

Hysteresis ::=							INTEGER (0..30)

-- ASN1STOP

LocationInfo-r10 ::=	SEQUENCE {
	locationCoordinates-r10					CHOICE {
		ellipsoid-Point-r10						OCTET STRING,
		ellipsoidPointWithAltitude-r10			OCTET STRING,
--	...,
		ellipsoidPointWithUncertaintyCircle-r11					OCTET STRING,
		ellipsoidPointWithUncertaintyEllipse-r11				OCTET STRING,
		ellipsoidPointWithAltitudeAndUncertaintyEllipsoid-r11	OCTET STRING,
		ellipsoidArc-r11			 							OCTET STRING,
		polygon-r11												OCTET STRING
	},
	horizontalVelocity-r10					OCTET STRING				OPTIONAL,
	gnss-TOD-msec-r10						OCTET STRING				OPTIONAL,
	...
}

-- ASN1STOP

MBSFN-RSRQ-Range-r12 ::=				INTEGER(0..31)
-- ASN1STOP

MeasConfig ::=						SEQUENCE {
	-- Measurement objects
	measObjectToRemoveList				MeasObjectToRemoveList				OPTIONAL,	-- Need ON
	measObjectToAddModList				MeasObjectToAddModList				OPTIONAL,	-- Need ON
	-- Reporting configurations
	reportConfigToRemoveList			ReportConfigToRemoveList			OPTIONAL,	-- Need ON
	reportConfigToAddModList			ReportConfigToAddModList			OPTIONAL,	-- Need ON
	-- Measurement identities
	measIdToRemoveList					MeasIdToRemoveList					OPTIONAL,	-- Need ON
	measIdToAddModList					MeasIdToAddModList					OPTIONAL,	-- Need ON
	-- Other parameters
	quantityConfig						QuantityConfig						OPTIONAL,	-- Need ON
	measGapConfig						MeasGapConfig						OPTIONAL,	-- Need ON
	s-Measure							RSRP-Range							OPTIONAL,	-- Need ON
	preRegistrationInfoHRPD				PreRegistrationInfoHRPD				OPTIONAL, 	-- Need OP
	speedStatePars			CHOICE {
		release								NULL,
		setup								SEQUENCE {
			mobilityStateParameters				MobilityStateParameters,
			timeToTrigger-SF					SpeedStateScaleFactors
		}
	}																		OPTIONAL,	-- Need ON
--	...,
	[[	measObjectToAddModList-v9e0			MeasObjectToAddModList-v9e0		OPTIONAL	-- Need ON
	]],
	[[	allowInterruptions-r11				BOOLEAN							OPTIONAL	-- Need ON
	]],
	[[	measScaleFactor-r12			CHOICE {
			release						NULL,
			setup						MeasScaleFactor-r12
		}																OPTIONAL,	-- Need ON
		measIdToRemoveListExt-r12			MeasIdToRemoveListExt-r12		OPTIONAL,	-- Need ON
		measIdToAddModListExt-r12			MeasIdToAddModListExt-r12		OPTIONAL,	-- Need ON
		measRSRQ-OnAllSymbols-r12		BOOLEAN							OPTIONAL	-- Need ON
	]],
	[[	ul-DelayConfig-r13			UL-DelayConfig-r13		OPTIONAL		-- Need ON
	]]
}

MeasIdToRemoveList ::=				SEQUENCE (SIZE (1..maxMeasId)) OF MeasId

MeasIdToRemoveListExt-r12 ::=		SEQUENCE (SIZE (1..maxMeasId)) OF MeasId-v1250

MeasObjectToRemoveList ::=			SEQUENCE (SIZE (1..maxObjectId)) OF MeasObjectId

ReportConfigToRemoveList ::=		SEQUENCE (SIZE (1..maxReportConfigId)) OF ReportConfigId

-- ASN1STOP

MeasDS-Config-r12 ::=			CHOICE {
	release							NULL,
	setup							SEQUENCE {
		dmtc-PeriodOffset-r12			CHOICE {
			ms40-r12						INTEGER(0..39),
			ms80-r12						INTEGER(0..79),
			ms160-r12						INTEGER(0..159),
			...
		},
		ds-OccasionDuration-r12		CHOICE {
			durationFDD-r12 				INTEGER(1..maxDS-Duration-r12),
			durationTDD-r12 				INTEGER(2..maxDS-Duration-r12)
		},
		measCSI-RS-ToRemoveList-r12	MeasCSI-RS-ToRemoveList-r12	OPTIONAL,	-- Need ON
		measCSI-RS-ToAddModList-r12	MeasCSI-RS-ToAddModList-r12	OPTIONAL,	-- Need ON
		...
	}
}

MeasCSI-RS-ToRemoveList-r12 ::=	SEQUENCE (SIZE (1..maxCSI-RS-Meas-r12)) OF MeasCSI-RS-Id-r12

MeasCSI-RS-ToAddModList-r12 ::=	SEQUENCE (SIZE (1..maxCSI-RS-Meas-r12)) OF MeasCSI-RS-Config-r12

MeasCSI-RS-Id-r12 ::=			INTEGER (1..maxCSI-RS-Meas-r12)

MeasCSI-RS-Config-r12 ::=		SEQUENCE {
	measCSI-RS-Id-r12				MeasCSI-RS-Id-r12,
	physCellId-r12					INTEGER (0..503),
	scramblingIdentity-r12			INTEGER (0..503),
	resourceConfig-r12				INTEGER (0..31),
	subframeOffset-r12				INTEGER (0..4),
	csi-RS-IndividualOffset-r12		Q-OffsetRange,
	...
}

-- ASN1STOP

MeasGapConfig ::=					CHOICE {
	release								NULL,
	setup								SEQUENCE {
		gapOffset							CHOICE {
				gp0									INTEGER (0..39),
				gp1									INTEGER (0..79),
				...
		}
	}
}

-- ASN1STOP

MeasId ::=							INTEGER (1..maxMeasId)

MeasId-v1250 ::=					INTEGER (maxMeasId-Plus1..maxMeasId-r12)

-- ASN1STOP

MeasIdToAddModList ::=				SEQUENCE (SIZE (1..maxMeasId)) OF MeasIdToAddMod

MeasIdToAddModListExt-r12 ::=		SEQUENCE (SIZE (1..maxMeasId)) OF MeasIdToAddModExt-r12

MeasIdToAddMod ::=	SEQUENCE {
	measId								MeasId,
	measObjectId						MeasObjectId,
	reportConfigId						ReportConfigId
}

MeasIdToAddModExt-r12 ::=	SEQUENCE {
	measId-v1250						MeasId-v1250,
	measObjectId-r12					MeasObjectId,
	reportConfigId-r12					ReportConfigId
}

-- ASN1STOP

MeasObjectCDMA2000 ::=				SEQUENCE {
	cdma2000-Type						CDMA2000-Type,
	carrierFreq							CarrierFreqCDMA2000,
	searchWindowSize					INTEGER (0..15)						OPTIONAL,	-- Need ON
	offsetFreq							Q-OffsetRangeInterRAT				DEFAULT 0,
	cellsToRemoveList					CellIndexList						OPTIONAL,	-- Need ON
	cellsToAddModList					CellsToAddModListCDMA2000			OPTIONAL,	-- Need ON
	cellForWhichToReportCGI				PhysCellIdCDMA2000					OPTIONAL,	-- Need ON
	...
}

CellsToAddModListCDMA2000 ::=		SEQUENCE (SIZE (1..maxCellMeas)) OF CellsToAddModCDMA2000

CellsToAddModCDMA2000 ::=	SEQUENCE {
	cellIndex							INTEGER (1..maxCellMeas),
	physCellId							PhysCellIdCDMA2000
}

-- ASN1STOP

MeasObjectEUTRA ::=					SEQUENCE {
	carrierFreq							ARFCN-ValueEUTRA,
	allowedMeasBandwidth				AllowedMeasBandwidth,
	presenceAntennaPort1				PresenceAntennaPort1,
	neighCellConfig						NeighCellConfig,
	offsetFreq							Q-OffsetRange				DEFAULT dB0,
	-- Cell list
	cellsToRemoveList					CellIndexList				OPTIONAL,		-- Need ON
	cellsToAddModList					CellsToAddModList			OPTIONAL,		-- Need ON
	-- Black list
	blackCellsToRemoveList				CellIndexList				OPTIONAL,		-- Need ON
	blackCellsToAddModList				BlackCellsToAddModList		OPTIONAL,		-- Need ON
	cellForWhichToReportCGI				PhysCellId					OPTIONAL,		-- Need ON
--	...,
	[[measCycleSCell-r10				MeasCycleSCell-r10		OPTIONAL,		-- Need ON
		measSubframePatternConfigNeigh-r10	MeasSubframePatternConfigNeigh-r10	OPTIONAL							-- Need ON
	]],
	[[widebandRSRQ-Meas-r11				BOOLEAN	OPTIONAL		-- Cond WB-RSRQ
	]],
	[[	altTTT-CellsToRemoveList-r12	CellIndexList				OPTIONAL,		-- Need ON
		altTTT-CellsToAddModList-r12	AltTTT-CellsToAddModList-r12	OPTIONAL,		-- Need ON
		t312-r12						CHOICE {
			release							NULL,
			setup							ENUMERATED {ms0, ms50, ms100, ms200,
											 ms300, ms400, ms500, ms1000}
		}														OPTIONAL,		-- Need ON
		reducedMeasPerformance-r12		BOOLEAN 					OPTIONAL,	 	-- Need ON
		measDS-Config-r12				MeasDS-Config-r12			OPTIONAL		-- Need ON
	]],
	[[	
		whiteCellsToRemoveList-r13		CellIndexList				OPTIONAL,		-- Need ON
		whiteCellsToAddModList-r13		WhiteCellsToAddModList-r13	OPTIONAL,		-- Need ON
		measRSSI-Config-r13				MeasRSSI-Config-r13			OPTIONAL		-- Need ON
	]]
}

MeasObjectEUTRA-v9e0 ::=			SEQUENCE {
	carrierFreq-v9e0					ARFCN-ValueEUTRA-v9e0
}

CellsToAddModList ::=				SEQUENCE (SIZE (1..maxCellMeas)) OF CellsToAddMod

CellsToAddMod ::=	SEQUENCE {
	cellIndex							INTEGER (1..maxCellMeas),
	physCellId							PhysCellId,
	cellIndividualOffset				Q-OffsetRange
}

BlackCellsToAddModList ::=			SEQUENCE (SIZE (1..maxCellMeas)) OF BlackCellsToAddMod

BlackCellsToAddMod ::=	SEQUENCE {
	cellIndex							INTEGER (1..maxCellMeas),
	physCellIdRange						PhysCellIdRange
}

MeasCycleSCell-r10 ::=				ENUMERATED {sf160, sf256, sf320, sf512,
													sf640, sf1024, sf1280, spare1}

MeasSubframePatternConfigNeigh-r10 ::=	CHOICE {
	release									NULL,
	setup									SEQUENCE {
		measSubframePatternNeigh-r10			MeasSubframePattern-r10,
		measSubframeCellList-r10				MeasSubframeCellList-r10	OPTIONAL	-- Cond always
	}
}

MeasSubframeCellList-r10 ::=	SEQUENCE (SIZE (1..maxCellMeas)) OF PhysCellIdRange

AltTTT-CellsToAddModList-r12 ::=	SEQUENCE (SIZE (1..maxCellMeas)) OF AltTTT-CellsToAddMod-r12

AltTTT-CellsToAddMod-r12 ::=	SEQUENCE {
	cellIndex-r12							INTEGER (1..maxCellMeas),
	physCellIdRange-r12						PhysCellIdRange
}

WhiteCellsToAddModList-r13 ::=			SEQUENCE (SIZE (1..maxCellMeas)) OF WhiteCellsToAddMod-r13

WhiteCellsToAddMod-r13 ::=	SEQUENCE {
	cellIndex-r13							INTEGER (1..maxCellMeas),
	physCellIdRange-r13						PhysCellIdRange
}

MeasRSSI-Config-r13 ::=	CHOICE {
	release								NULL,
	setup								SEQUENCE {
		rmtc-Period-r13					ENUMERATED {ms40, ms80, ms160, ms320, ms640},
		rmtc-SubframeOffset-r13			INTEGER(0..639)					OPTIONAL, 		-- Need ON
		measDuration-r13				ENUMERATED {sym1, sym14, sym28, sym42, sym70}
	}
}

-- ASN1STOP

MeasObjectGERAN ::=					SEQUENCE {
	carrierFreqs						CarrierFreqsGERAN,
	offsetFreq							Q-OffsetRangeInterRAT		DEFAULT 0,
	ncc-Permitted						BIT STRING(SIZE (8))		DEFAULT '11111111'B,
	cellForWhichToReportCGI				PhysCellIdGERAN				OPTIONAL, 	-- Need ON
	...
}

-- ASN1STOP

MeasObjectId ::=					INTEGER (1..maxObjectId)

-- ASN1STOP

MeasObjectToAddModList ::=			SEQUENCE (SIZE (1..maxObjectId)) OF MeasObjectToAddMod

MeasObjectToAddModList-v9e0 ::=		SEQUENCE (SIZE (1..maxObjectId)) OF MeasObjectToAddMod-v9e0

MeasObjectToAddMod ::=	SEQUENCE {
	measObjectId						MeasObjectId,
	measObject							CHOICE {
		measObjectEUTRA						MeasObjectEUTRA,
		measObjectUTRA						MeasObjectUTRA,
		measObjectGERAN						MeasObjectGERAN,
		measObjectCDMA2000					MeasObjectCDMA2000,
		...
	}
}

MeasObjectToAddMod-v9e0 ::=	SEQUENCE {
	measObjectEUTRA-v9e0				MeasObjectEUTRA-v9e0		OPTIONAL	-- Cond eutra
}

-- ASN1STOP

MeasObjectUTRA ::=					SEQUENCE {
	carrierFreq							ARFCN-ValueUTRA,
	offsetFreq							Q-OffsetRangeInterRAT		DEFAULT 0,
	cellsToRemoveList					CellIndexList				OPTIONAL,			-- Need ON
	cellsToAddModList					CHOICE {
		cellsToAddModListUTRA-FDD			CellsToAddModListUTRA-FDD,
		cellsToAddModListUTRA-TDD			CellsToAddModListUTRA-TDD
	}																OPTIONAL,			-- Need ON
	cellForWhichToReportCGI				CHOICE {
		utra-FDD							PhysCellIdUTRA-FDD,
		utra-TDD							PhysCellIdUTRA-TDD
	}																OPTIONAL, 	-- Need ON
--	...,
	[[	csg-allowedReportingCells-v930			CSG-AllowedReportingCells-r9	OPTIONAL		-- Need ON
	]],
	[[	reducedMeasPerformance-r12				BOOLEAN 			OPTIONAL	 	-- Need ON
	]]
}

CellsToAddModListUTRA-FDD ::=		SEQUENCE (SIZE (1..maxCellMeas)) OF CellsToAddModUTRA-FDD 

CellsToAddModUTRA-FDD ::=	SEQUENCE {
	cellIndex							INTEGER (1..maxCellMeas),
	physCellId							PhysCellIdUTRA-FDD
}

CellsToAddModListUTRA-TDD ::=		SEQUENCE (SIZE (1..maxCellMeas)) OF CellsToAddModUTRA-TDD 

CellsToAddModUTRA-TDD ::=	SEQUENCE {
	cellIndex							INTEGER (1..maxCellMeas),
	physCellId							PhysCellIdUTRA-TDD
}

CSG-AllowedReportingCells-r9 ::=		SEQUENCE {
	physCellIdRangeUTRA-FDDList-r9			PhysCellIdRangeUTRA-FDDList-r9	OPTIONAL	-- Need OR
}
-- ASN1STOP

MeasResults ::=						SEQUENCE {
	measId								MeasId,
	measResultPCell					SEQUENCE {
		rsrpResult							RSRP-Range,
		rsrqResult							RSRQ-Range
	},
	measResultNeighCells				CHOICE {
		measResultListEUTRA					MeasResultListEUTRA,
		measResultListUTRA					MeasResultListUTRA,
		measResultListGERAN					MeasResultListGERAN,
		measResultsCDMA2000					MeasResultsCDMA2000,
		...
	}																		OPTIONAL,
--	...,
	[[	measResultForECID-r9				MeasResultForECID-r9			OPTIONAL
	]],
	[[	locationInfo-r10					LocationInfo-r10				OPTIONAL,
		measResultServFreqList-r10			MeasResultServFreqList-r10		OPTIONAL
	]],
	[[	measId-v1250						MeasId-v1250					OPTIONAL,
		measResultPCell-v1250				RSRQ-Range-v1250				OPTIONAL,
		measResultCSI-RS-List-r12			MeasResultCSI-RS-List-r12		OPTIONAL
	]],
	[[	measResultForRSSI-r13				MeasResultForRSSI-r13			OPTIONAL,
		measResultServFreqListExt-r13		MeasResultServFreqListExt-r13		OPTIONAL,
		measResultSSTD-r13					MeasResultSSTD-r13				OPTIONAL,
		measResultPCell-v13xy				SEQUENCE {
			rs-sinrResult-r13					RS-SINR-Range-r13
		}																	OPTIONAL,
		ul-PDCP-DelayResultList-r13			UL-PDCP-DelayResultList-r13		OPTIONAL
	]]

}

MeasResultListEUTRA ::=				SEQUENCE (SIZE (1..maxCellReport)) OF MeasResultEUTRA 

MeasResultEUTRA ::=	SEQUENCE {
	physCellId							PhysCellId,
	cgi-Info							SEQUENCE {
		cellGlobalId						CellGlobalIdEUTRA,
		trackingAreaCode					TrackingAreaCode,
		plmn-IdentityList					PLMN-IdentityList2 				OPTIONAL
	}			 												OPTIONAL,
	measResult							SEQUENCE {
		rsrpResult							RSRP-Range						OPTIONAL,
		rsrqResult							RSRQ-Range						OPTIONAL,
	--	...,
		[[	additionalSI-Info-r9				AdditionalSI-Info-r9				OPTIONAL
		]],
		[[	primaryPLMN-Suitable-r12			ENUMERATED {true}			OPTIONAL,
			measResult-v1250					RSRQ-Range-v1250			OPTIONAL
		]],
		[[	rs-sinrResult-r13					RS-SINR-Range-r13			OPTIONAL
		]]
	}
}

MeasResultServFreqList-r10 ::=	SEQUENCE (SIZE (1..maxServCell-r10)) OF MeasResultServFreq-r10

MeasResultServFreqListExt-r13 ::=	SEQUENCE (SIZE (maxServCell-Plus1..maxServCell-r13)) OF MeasResultServFreq-r13

MeasResultServFreq-r10 ::=			SEQUENCE {
	servFreqId-r10						ServCellIndex-r10,
	measResultSCell-r10					SEQUENCE {
		rsrpResultSCell-r10					RSRP-Range,
		rsrqResultSCell-r10					RSRQ-Range
	}															OPTIONAL,
	measResultBestNeighCell-r10			SEQUENCE {
		physCellId-r10						PhysCellId,
		rsrpResultNCell-r10					RSRP-Range,
		rsrqResultNCell-r10					RSRQ-Range
	}															OPTIONAL,
--	...,
	[[	measResultSCell-v1250				RSRQ-Range-v1250	OPTIONAL,
		measResultBestNeighCell-v1250		RSRQ-Range-v1250	OPTIONAL
	]],
	[[	measResultSCell-v13xy				SEQUENCE {
			rs-sinrResult-r13					RS-SINR-Range-r13
		}		OPTIONAL,
		measResultBestNeighCell-v13xy		SEQUENCE {
			rs-sinrResult-r13					RS-SINR-Range-r13
		}		OPTIONAL
	]]
}

MeasResultServFreq-r13 ::=			SEQUENCE {
	servFreqId-r13						ServCellIndexFull-r13,
	measResultSCell-r13					SEQUENCE {
		rsrpResultSCell-r13					RSRP-Range,
		rsrqResultSCell-r13					RSRQ-Range-v13xx,
		rs-sinrResult-r13					RS-SINR-Range-r13	OPTIONAL
	}															OPTIONAL,
	measResultBestNeighCell-r13			SEQUENCE {
		physCellId-r13						PhysCellId,
		rsrpResultNCell-r10					RSRP-Range,
		rsrqResultNCell-r13					RSRQ-Range-v13xx,
		rs-sinrResult-r13					RS-SINR-Range-r13	OPTIONAL
	}															OPTIONAL,
	...
}

MeasResultCSI-RS-List-r12 ::=	SEQUENCE (SIZE (1..maxCellReport)) OF MeasResultCSI-RS-r12

MeasResultCSI-RS-r12 ::=		SEQUENCE {
	measCSI-RS-Id-r12				MeasCSI-RS-Id-r12,
	csi-RSRP-Result-r12				CSI-RSRP-Range-r12,
	...
}

MeasResultListUTRA ::=				SEQUENCE (SIZE (1..maxCellReport)) OF MeasResultUTRA 

MeasResultUTRA ::=	SEQUENCE {
	physCellId							CHOICE {
		fdd									PhysCellIdUTRA-FDD,
		tdd									PhysCellIdUTRA-TDD
	},
	cgi-Info							SEQUENCE {
		cellGlobalId						CellGlobalIdUTRA,
		locationAreaCode					BIT STRING (SIZE (16))			OPTIONAL,
		routingAreaCode						BIT STRING (SIZE (8))			OPTIONAL,
		plmn-IdentityList					PLMN-IdentityList2 				OPTIONAL
	}			 												OPTIONAL,
	measResult							SEQUENCE {
		utra-RSCP							INTEGER (-5..91)				OPTIONAL,
		utra-EcN0							INTEGER (0..49)					OPTIONAL,
	--	...,
		[[	additionalSI-Info-r9				AdditionalSI-Info-r9				OPTIONAL
		]],
		[[	primaryPLMN-Suitable-r12			ENUMERATED {true}			OPTIONAL
		]]
	}
}

MeasResultListGERAN ::=				SEQUENCE (SIZE (1..maxCellReport)) OF MeasResultGERAN 

MeasResultGERAN ::=	SEQUENCE {
	carrierFreq							CarrierFreqGERAN,
	physCellId							PhysCellIdGERAN,
	cgi-Info							SEQUENCE {
		cellGlobalId						CellGlobalIdGERAN,
		routingAreaCode						BIT STRING (SIZE (8))			OPTIONAL
	}			 															OPTIONAL,
	measResult							SEQUENCE {
		rssi								INTEGER (0..63),
		...
	}
}

MeasResultsCDMA2000 ::=				SEQUENCE {
	preRegistrationStatusHRPD			BOOLEAN,
	measResultListCDMA2000				MeasResultListCDMA2000
}

MeasResultListCDMA2000 ::=			SEQUENCE (SIZE (1..maxCellReport)) OF MeasResultCDMA2000

MeasResultCDMA2000 ::=	SEQUENCE {
	physCellId							PhysCellIdCDMA2000,
	cgi-Info							CellGlobalIdCDMA2000		 		OPTIONAL,
	measResult							SEQUENCE {
		pilotPnPhase						INTEGER	(0..32767)				OPTIONAL,
		pilotStrength						INTEGER (0..63),
		...
	}
}

MeasResultForECID-r9 ::=		SEQUENCE {
	ue-RxTxTimeDiffResult-r9				INTEGER (0..4095),
	currentSFN-r9							BIT STRING (SIZE (10))
}

PLMN-IdentityList2 ::=				SEQUENCE (SIZE (1..5)) OF PLMN-Identity

AdditionalSI-Info-r9 ::=			SEQUENCE {
	csg-MemberStatus-r9				ENUMERATED {member}				OPTIONAL,
	csg-Identity-r9						CSG-Identity						OPTIONAL
}
MeasResultForRSSI-r13 ::=			SEQUENCE {
	rssi-Result-r13							RSSI-Range-r13, 
	channelOccupancy-r13					INTEGER (0..100)
}

UL-PDCP-DelayResultList-r13 ::=		SEQUENCE (SIZE (1..maxQCI-r13)) OF UL-PDCP-DelayResult-r13


UL-PDCP-DelayResult-r13 ::=			SEQUENCE {
	qci-Id-r13							ENUMERATED {qci1, qci2, qci3, qci4, spare4, spare3, spare2, spare1},
	excessDelay-r13						INTEGER (0..31) 
}

-- ASN1STOP

MeasResultSSTD-r13 ::=						SEQUENCE {
	sfn-OffsetResult-r13						INTEGER (0..1023),
	frameBoundaryOffsetResult-r13				INTEGER (-4..5),
	subframeBoundaryOffsetResult-r13			INTEGER (0..63)
}

-- ASN1STOP

MeasScaleFactor-r12 ::=			ENUMERATED {sf-EUTRA-cf1, sf-EUTRA-cf2}

-- ASN1STOP

QuantityConfig ::=					SEQUENCE {
	quantityConfigEUTRA					QuantityConfigEUTRA					OPTIONAL,	-- Need ON
	quantityConfigUTRA					QuantityConfigUTRA					OPTIONAL,	-- Need ON
	quantityConfigGERAN					QuantityConfigGERAN					OPTIONAL,	-- Need ON
	quantityConfigCDMA2000				QuantityConfigCDMA2000				OPTIONAL,	-- Need ON
--	...,
	[[	quantityConfigUTRA-v1020		QuantityConfigUTRA-v1020			OPTIONAL	-- Need ON
	]],
	[[	quantityConfigEUTRA-v1250		QuantityConfigEUTRA-v1250			OPTIONAL	-- Need ON
	]],
	[[	quantityConfigEUTRA-v13xy		QuantityConfigEUTRA-v13xy			OPTIONAL	-- Need ON
	]]
}

QuantityConfigEUTRA ::=				SEQUENCE {
	filterCoefficientRSRP				FilterCoefficient					DEFAULT fc4,
	filterCoefficientRSRQ				FilterCoefficient					DEFAULT fc4
}

QuantityConfigEUTRA-v1250 ::=		SEQUENCE {
	filterCoefficientCSI-RSRP-r12		FilterCoefficient					OPTIONAL		-- Need OR
}

QuantityConfigEUTRA-v13xy ::=		SEQUENCE {
	filterCoefficientRS-SINR-r13		FilterCoefficient					DEFAULT fc4
}

QuantityConfigUTRA ::=				SEQUENCE {
	measQuantityUTRA-FDD				ENUMERATED {cpich-RSCP, cpich-EcN0},
	measQuantityUTRA-TDD				ENUMERATED {pccpch-RSCP},
	filterCoefficient					FilterCoefficient					DEFAULT fc4
}

QuantityConfigUTRA-v1020 ::=		SEQUENCE {
	filterCoefficient2-FDD-r10			FilterCoefficient					DEFAULT fc4
}

QuantityConfigGERAN ::=				SEQUENCE {
	measQuantityGERAN					ENUMERATED {rssi},
	filterCoefficient					FilterCoefficient					DEFAULT fc2
}

QuantityConfigCDMA2000 ::=			SEQUENCE {
	measQuantityCDMA2000				ENUMERATED {pilotStrength, pilotPnPhaseAndPilotStrength}
}

-- ASN1STOP

ReportConfigEUTRA ::=				SEQUENCE {
	triggerType							CHOICE {
		event								SEQUENCE {
			eventId								CHOICE {
				eventA1								SEQUENCE {
					a1-Threshold						ThresholdEUTRA
				},
				eventA2								SEQUENCE {
					a2-Threshold						ThresholdEUTRA
				},
				eventA3								SEQUENCE {
					a3-Offset							INTEGER (-30..30),
					reportOnLeave						BOOLEAN
				},
				eventA4								SEQUENCE {
					a4-Threshold						ThresholdEUTRA
				},
				eventA5								SEQUENCE {
					a5-Threshold1						ThresholdEUTRA,
					a5-Threshold2						ThresholdEUTRA
				},
			--	...,
				eventA6-r10							SEQUENCE {
					a6-Offset-r10						INTEGER (-30..30),
					a6-ReportOnLeave-r10				BOOLEAN
				},
				eventC1-r12							SEQUENCE {
					c1-Threshold-r12					ThresholdEUTRA-v1250,
					c1-ReportOnLeave-r12				BOOLEAN
				},
				eventC2-r12							SEQUENCE {
					c2-RefCSI-RS-r12					MeasCSI-RS-Id-r12,
					c2-Offset-r12						INTEGER (-30..30),
					c2-ReportOnLeave-r12				BOOLEAN
				}
			},
			hysteresis							Hysteresis,
			timeToTrigger						TimeToTrigger
		},
		periodical								SEQUENCE {
			purpose									ENUMERATED {
														reportStrongestCells, reportCGI}
		}
	},
	triggerQuantity						ENUMERATED {rsrp, rsrq},
	reportQuantity						ENUMERATED {sameAsTriggerQuantity, both},
	maxReportCells						INTEGER (1..maxCellReport),
	reportInterval						ReportInterval,
	reportAmount						ENUMERATED {r1, r2, r4, r8, r16, r32, r64, infinity},
--	...,
	[[	si-RequestForHO-r9					ENUMERATED {setup}		OPTIONAL,	-- Cond reportCGI
		ue-RxTxTimeDiffPeriodical-r9		ENUMERATED {setup}		OPTIONAL	-- Need OR
	]],
	[[	includeLocationInfo-r10		 		ENUMERATED {true}		OPTIONAL,	-- Need OR
		reportAddNeighMeas-r10				ENUMERATED {setup}		OPTIONAL	-- Need OR
	]],
	[[	alternativeTimeToTrigger-r12		CHOICE {
			release								NULL,
			setup								TimeToTrigger
		}													OPTIONAL,	-- Need ON
		useT312-r12							BOOLEAN			OPTIONAL,	-- Need ON
		usePSCell-r12						BOOLEAN			OPTIONAL, 	-- Need ON
		aN-Threshold1-v1250					RSRQ-RangeConfig-r12		OPTIONAL, 	-- Need ON
		a5-Threshold2-v1250					RSRQ-RangeConfig-r12		OPTIONAL, 	-- Need ON
		reportStrongestCSI-RSs-r12			BOOLEAN		OPTIONAL,	-- Need ON
		reportCRS-Meas-r12					BOOLEAN		OPTIONAL,	-- Need ON
		triggerQuantityCSI-RS-r12			BOOLEAN			OPTIONAL		-- Need ON
	]],
	[[	reportSSTD-Meas-r13					BOOLEAN			OPTIONAL,		-- Need ON
		triggerQuantity-v13xy			CHOICE {
			release							NULL,
			setup							ENUMERATED {sinr}
		}													OPTIONAL,	-- Need ON
		aN-ThresholdSINR-r13			CHOICE {
			release							NULL,
			setup							SEQUENCE {
				threshold1-r13					ThresholdEUTRA-v13xy		OPTIONAL, 	-- Need ON
				threshold2-r13					ThresholdEUTRA-v13xy		OPTIONAL 	-- Need ON
			}
		}													OPTIONAL,	-- Cond SINR
		reportQuantity-v13xy			CHOICE {
			release							NULL,
			setup							ENUMERATED {rsrpANDsinr, rsrqANDsinr, all}
		}													OPTIONAL,	-- Need ON
		useWhiteCellList-r13				BOOLEAN			OPTIONAL,	-- Need ON
		measRSSI-ReportConfig-r13			MeasRSSI-ReportConfig-r13	OPTIONAL	-- Need OR
	]]
}

RSRQ-RangeConfig-r12 ::=			CHOICE {
	release								NULL,
	setup								RSRQ-Range-v1250
}

ThresholdEUTRA ::=					CHOICE{
	threshold-RSRP						RSRP-Range,
	threshold-RSRQ						RSRQ-Range
}

ThresholdEUTRA-v1250 ::=			CSI-RSRP-Range-r12

ThresholdEUTRA-v13xy ::=			RS-SINR-Range-r13

MeasRSSI-ReportConfig-r13 ::=	SEQUENCE {
	channelOccupancyThreshold-r13			RSSI-Range-r13
}

-- ASN1STOP

ReportConfigId ::=					INTEGER (1..maxReportConfigId)

-- ASN1STOP

ReportConfigInterRAT ::=			SEQUENCE {
	triggerType							CHOICE {
		event								SEQUENCE {
			eventId								CHOICE {
				eventB1								SEQUENCE {
					b1-Threshold						CHOICE {
						b1-ThresholdUTRA					ThresholdUTRA,
						b1-ThresholdGERAN					ThresholdGERAN,
						b1-ThresholdCDMA2000				ThresholdCDMA2000
					}
				},
				eventB2								SEQUENCE {
					b2-Threshold1						ThresholdEUTRA,
					b2-Threshold2						CHOICE {
						b2-Threshold2UTRA					ThresholdUTRA,
						b2-Threshold2GERAN					ThresholdGERAN,
						b2-Threshold2CDMA2000				ThresholdCDMA2000
					}
				},
				...
			},
			hysteresis						Hysteresis,
			timeToTrigger					TimeToTrigger
		},
		periodical								SEQUENCE {
			purpose									ENUMERATED {
														reportStrongestCells,
														reportStrongestCellsForSON,
														reportCGI}
		}
	},
	maxReportCells						INTEGER (1..maxCellReport),
	reportInterval						ReportInterval,	
	reportAmount						ENUMERATED {r1, r2, r4, r8, r16, r32, r64, infinity},
--	...,
	[[	si-RequestForHO-r9					ENUMERATED {setup}		OPTIONAL	-- Cond reportCGI
	]],
	[[	reportQuantityUTRA-FDD-r10			ENUMERATED {both}		OPTIONAL	-- Need OR
	]],
	[[	includeLocationInfo-r11		 		BOOLEAN					OPTIONAL	-- Need ON
	]],
	[[	b2-Threshold1-v1250					CHOICE {
			release								NULL,
			setup								RSRQ-Range-v1250
		}															OPTIONAL 	-- Need ON
	]]
}

ThresholdUTRA ::=					CHOICE{
	utra-RSCP							INTEGER (-5..91),
	utra-EcN0							INTEGER (0..49)
}

ThresholdGERAN ::= 				INTEGER (0..63)

ThresholdCDMA2000 ::= 			INTEGER (0..63)

-- ASN1STOP

ReportConfigToAddModList ::=		SEQUENCE (SIZE (1..maxReportConfigId)) OF ReportConfigToAddMod

ReportConfigToAddMod ::=	SEQUENCE {
	reportConfigId						ReportConfigId,
	reportConfig						CHOICE {
		reportConfigEUTRA					ReportConfigEUTRA,
		reportConfigInterRAT				ReportConfigInterRAT
	}
}


-- ASN1STOP

ReportInterval ::=					ENUMERATED {
										ms120, ms240, ms480, ms640, ms1024, ms2048, ms5120, ms10240,
										min1, min6, min12, min30, min60, spare3, spare2, spare1}

-- ASN1STOP

RSRP-Range ::=						INTEGER(0..97)

RSRP-RangeSL-r12 ::=				INTEGER(0..13)

RSRP-RangeSL2-r12 ::=				INTEGER(0..7)

RSRP-RangeSL3-r12 ::=				INTEGER(0..11)

-- ASN1STOP

RSRQ-Range ::=						INTEGER(0..34)

RSRQ-Range-v1250 ::=				INTEGER(-30..46)

RSRQ-Range-v13xx ::=				INTEGER(-30..46)

-- ASN1STOP

RSRQ-Type-r12 ::=					SEQUENCE {
	allSymbols-r12							BOOLEAN,
	wideBand-r12							BOOLEAN
}

-- ASN1STOP

RS-SINR-Range-r13 ::=						INTEGER(0..127)

-- ASN1STOP

RSSI-Range-r13 ::=						INTEGER(0..76)

-- ASN1STOP

TimeToTrigger ::=					ENUMERATED {
										ms0, ms40, ms64, ms80, ms100, ms128, ms160, ms256,
										ms320, ms480, ms512, ms640, ms1024, ms1280, ms2560,
										ms5120}

-- ASN1STOP

UL-DelayConfig-r13 ::=					CHOICE {
		release								NULL,
		setup								SEQUENCE {
			delayThreshold-r13							ENUMERATED {
												ms30, ms40, ms50, ms60, ms70, ms80, 
												ms90,ms100, ms150, ms300, ms500, ms750, spare4,												spare3, spare2, spare1},
			delayReportInterval-r13						ENUMERATED {
												ms1024, ms2048, ms5120, ms10240}
		}
}

-- ASN1STOP

AbsoluteTimeInfo-r10 ::=				BIT STRING (SIZE (48))

-- ASN1STOP

AreaConfiguration-r10 ::=	CHOICE {
	cellGlobalIdList-r10			CellGlobalIdList-r10,
	trackingAreaCodeList-r10		TrackingAreaCodeList-r10
}

AreaConfiguration-v1130 ::=		SEQUENCE {
	trackingAreaCodeList-v1130		TrackingAreaCodeList-v1130
}

CellGlobalIdList-r10 ::=				SEQUENCE (SIZE (1..32)) OF CellGlobalIdEUTRA

TrackingAreaCodeList-r10 ::=			SEQUENCE (SIZE (1..8)) OF TrackingAreaCode

TrackingAreaCodeList-v1130 ::=	SEQUENCE {
	plmn-Identity-perTAC-List-r11			SEQUENCE (SIZE (1..8)) OF PLMN-Identity
}

-- ASN1STOP

C-RNTI ::=							BIT STRING (SIZE (16))

-- ASN1STOP

DedicatedInfoCDMA2000 ::=				OCTET STRING

-- ASN1STOP

DedicatedInfoNAS ::=		OCTET STRING

-- ASN1STOP

FilterCoefficient ::=					ENUMERATED {
											fc0, fc1, fc2, fc3, fc4, fc5,
											fc6, fc7, fc8, fc9, fc11, fc13, 
											fc15, fc17, fc19, spare1, ...}

-- ASN1STOP

LoggingDuration-r10 ::=			ENUMERATED {
									min10, min20, min40, min60, min90, min120, spare2, spare1}

-- ASN1STOP

LoggingInterval-r10 ::=			ENUMERATED {
									ms1280, ms2560, ms5120, ms10240, ms20480,
									ms30720, ms40960, ms61440}

-- ASN1STOP

MeasSubframePattern-r10 ::= CHOICE {
	subframePatternFDD-r10				BIT STRING (SIZE (40)),
	subframePatternTDD-r10				CHOICE {
		subframeConfig1-5-r10					BIT STRING (SIZE (20)),
		subframeConfig0-r10						BIT STRING (SIZE (70)),
		subframeConfig6-r10						BIT STRING (SIZE (60)),
		...
	},
	...
}

-- ASN1STOP

MMEC ::=							BIT STRING (SIZE (8))

-- ASN1STOP

NeighCellConfig ::=			BIT STRING (SIZE (2))

-- ASN1STOP

OtherConfig-r9 ::= SEQUENCE	{
	reportProximityConfig-r9			ReportProximityConfig-r9		OPTIONAL,	-- Need ON
--	...,
	[[	idc-Config-r11					IDC-Config-r11					OPTIONAL,	-- Need ON
		powerPrefIndicationConfig-r11	PowerPrefIndicationConfig-r11	OPTIONAL,	-- Need ON
		obtainLocationConfig-r11		ObtainLocationConfig-r11		OPTIONAL	-- Need ON
	]]
}

IDC-Config-r11 ::= 				SEQUENCE {
	idc-Indication-r11					ENUMERATED {setup}		OPTIONAL,		-- Need OR
	autonomousDenialParameters-r11		SEQUENCE {
			autonomousDenialSubframes-r11			ENUMERATED {n2, n5, n10, n15,
														n20, n30, spare2, spare1},
			autonomousDenialValidity-r11			ENUMERATED {
														sf200, sf500, sf1000, sf2000, 
														spare4, spare3, spare2, spare1}
	}		OPTIONAL, 		-- Need OR
--	...,
	[[	idc-Indication-UL-CA-r11		ENUMERATED {setup}		OPTIONAL		-- Cond idc-Ind
	]]
}

ObtainLocationConfig-r11 ::= SEQUENCE {
	obtainLocation-r11				ENUMERATED {setup}				OPTIONAL		-- Need OR
}

PowerPrefIndicationConfig-r11 ::= CHOICE{
	release					NULL,
	setup					SEQUENCE{
		powerPrefIndicationTimer-r11		ENUMERATED {s0, s0dot5, s1, s2, s5, s10, s20, 
											s30, s60, s90, s120, s300, s600, spare3, 
											spare2, spare1}
	}
}

ReportProximityConfig-r9 ::= SEQUENCE {
	proximityIndicationEUTRA-r9		ENUMERATED {enabled}			OPTIONAL,		-- Need OR
	proximityIndicationUTRA-r9		ENUMERATED {enabled}			OPTIONAL		-- Need OR
}

-- ASN1STOP

RAND-CDMA2000 ::=						BIT STRING (SIZE (32))

-- ASN1STOP

RAT-Type ::=						ENUMERATED {
										eutra, utra, geran-cs, geran-ps, cdma2000-1XRTT,
										spare3, spare2, spare1, ...}

-- ASN1STOP

RRC-TransactionIdentifier ::=		INTEGER (0..3)

-- ASN1STOP

S-TMSI ::=							SEQUENCE {
	mmec								MMEC,
	m-TMSI								BIT STRING (SIZE (32))
}

-- ASN1STOP

TraceReference-r10 ::=			SEQUENCE {
	plmn-Identity-r10				PLMN-Identity,
	traceId-r10						OCTET STRING (SIZE (3))
}

-- ASN1STOP

UE-CapabilityRAT-ContainerList ::=SEQUENCE (SIZE (0..maxRAT-Capabilities)) OF UE-CapabilityRAT-Container

UE-CapabilityRAT-Container ::= SEQUENCE {
	rat-Type							RAT-Type,
	ueCapabilityRAT-Container			OCTET STRING
}

-- ASN1STOP

UE-EUTRA-Capability ::=			SEQUENCE {
	accessStratumRelease				AccessStratumRelease,
	ue-Category							INTEGER (1..5),
	pdcp-Parameters						PDCP-Parameters,
	phyLayerParameters					PhyLayerParameters,
	rf-Parameters						RF-Parameters,
	measParameters						MeasParameters,
	featureGroupIndicators				BIT STRING (SIZE (32))				OPTIONAL,
	interRAT-Parameters				SEQUENCE {
		utraFDD								IRAT-ParametersUTRA-FDD				OPTIONAL,
		utraTDD128							IRAT-ParametersUTRA-TDD128				OPTIONAL,
		utraTDD384							IRAT-ParametersUTRA-TDD384				OPTIONAL,
		utraTDD768							IRAT-ParametersUTRA-TDD768				OPTIONAL,
		geran								IRAT-ParametersGERAN					OPTIONAL,
		cdma2000-HRPD						IRAT-ParametersCDMA2000-HRPD			OPTIONAL,
		cdma2000-1xRTT						IRAT-ParametersCDMA2000-1XRTT			OPTIONAL
	},
	nonCriticalExtension				UE-EUTRA-Capability-v920-IEs		OPTIONAL
}

-- Late non critical extensions
UE-EUTRA-Capability-v9a0-IEs ::=	SEQUENCE {
	featureGroupIndRel9Add-r9			BIT STRING (SIZE (32))				OPTIONAL,
	fdd-Add-UE-EUTRA-Capabilities-r9	UE-EUTRA-CapabilityAddXDD-Mode-r9	OPTIONAL,
	tdd-Add-UE-EUTRA-Capabilities-r9	UE-EUTRA-CapabilityAddXDD-Mode-r9	OPTIONAL,
	nonCriticalExtension				UE-EUTRA-Capability-v9c0-IEs		OPTIONAL
}

UE-EUTRA-Capability-v9c0-IEs ::=		SEQUENCE {
	interRAT-ParametersUTRA-v9c0		IRAT-ParametersUTRA-v9c0		OPTIONAL,
	nonCriticalExtension				UE-EUTRA-Capability-v9d0-IEs	OPTIONAL
}

UE-EUTRA-Capability-v9d0-IEs ::=		SEQUENCE {
	phyLayerParameters-v9d0				PhyLayerParameters-v9d0			OPTIONAL,
	nonCriticalExtension				UE-EUTRA-Capability-v9e0-IEs	OPTIONAL
}

UE-EUTRA-Capability-v9e0-IEs ::=	SEQUENCE {
	rf-Parameters-v9e0					RF-Parameters-v9e0						OPTIONAL,
	nonCriticalExtension				UE-EUTRA-Capability-v9h0-IEs			OPTIONAL
}

UE-EUTRA-Capability-v9h0-IEs ::=	SEQUENCE {
	interRAT-ParametersUTRA-v9h0		IRAT-ParametersUTRA-v9h0			OPTIONAL,
	-- Following field is only to be used for late REL-9 extensions
	lateNonCriticalExtension			OCTET STRING							OPTIONAL,
	nonCriticalExtension				UE-EUTRA-Capability-v10c0-IEs			OPTIONAL
}

UE-EUTRA-Capability-v10c0-IEs ::=	SEQUENCE {
	otdoa-PositioningCapabilities-r10	OTDOA-PositioningCapabilities-r10		OPTIONAL,
	nonCriticalExtension				UE-EUTRA-Capability-v10f0-IEs			OPTIONAL
}

UE-EUTRA-Capability-v10f0-IEs ::=	SEQUENCE {
	rf-Parameters-v10f0					RF-Parameters-v10f0						OPTIONAL,
	nonCriticalExtension				UE-EUTRA-Capability-v10i0-IEs			OPTIONAL
}

UE-EUTRA-Capability-v10i0-IEs ::=	SEQUENCE {
	rf-Parameters-v10i0					RF-Parameters-v10i0						OPTIONAL,
	-- Following field is only to be used for late REL-10 extensions
	lateNonCriticalExtension			OCTET STRING (CONTAINING UE-EUTRA-Capability-v10j0-IEs)	OPTIONAL,
	nonCriticalExtension				UE-EUTRA-Capability-v11d0-IEs			OPTIONAL
}

UE-EUTRA-Capability-v10j0-IEs ::=	SEQUENCE {
	rf-Parameters-v10j0					RF-Parameters-v10j0						OPTIONAL,
	nonCriticalExtension				SEQUENCE {}								OPTIONAL
}

UE-EUTRA-Capability-v11d0-IEs ::=	SEQUENCE {
	rf-Parameters-v11d0					RF-Parameters-v11d0						OPTIONAL,
	otherParameters-v11d0				Other-Parameters-v11d0					OPTIONAL,
	-- Following field is only to be used for late REL-11 extensions
	nonCriticalExtension				SEQUENCE {}								OPTIONAL
}

-- Regular non critical extensions
UE-EUTRA-Capability-v920-IEs ::=		SEQUENCE {
	phyLayerParameters-v920				PhyLayerParameters-v920,
	interRAT-ParametersGERAN-v920			IRAT-ParametersGERAN-v920,
	interRAT-ParametersUTRA-v920			IRAT-ParametersUTRA-v920			OPTIONAL,
	interRAT-ParametersCDMA2000-v920		IRAT-ParametersCDMA2000-1XRTT-v920	OPTIONAL,
	deviceType-r9							ENUMERATED {noBenFromBatConsumpOpt}	OPTIONAL,
	csg-ProximityIndicationParameters-r9	CSG-ProximityIndicationParameters-r9,
	neighCellSI-AcquisitionParameters-r9	NeighCellSI-AcquisitionParameters-r9,
	son-Parameters-r9						SON-Parameters-r9,
	nonCriticalExtension					UE-EUTRA-Capability-v940-IEs		OPTIONAL
}

UE-EUTRA-Capability-v940-IEs ::=	SEQUENCE {
	lateNonCriticalExtension			OCTET STRING (CONTAINING UE-EUTRA-Capability-v9a0-IEs)
																			OPTIONAL,
	nonCriticalExtension				UE-EUTRA-Capability-v1020-IEs		OPTIONAL
}

UE-EUTRA-Capability-v1020-IEs ::=	SEQUENCE {
	ue-Category-v1020					INTEGER (6..8)							OPTIONAL,
	phyLayerParameters-v1020			PhyLayerParameters-v1020				OPTIONAL,
	rf-Parameters-v1020					RF-Parameters-v1020						OPTIONAL,
	measParameters-v1020				MeasParameters-v1020					OPTIONAL,
	featureGroupIndRel10-r10			BIT STRING (SIZE (32))					OPTIONAL,
	interRAT-ParametersCDMA2000-v1020	IRAT-ParametersCDMA2000-1XRTT-v1020		OPTIONAL,
	ue-BasedNetwPerfMeasParameters-r10	UE-BasedNetwPerfMeasParameters-r10		OPTIONAL,
	interRAT-ParametersUTRA-TDD-v1020	IRAT-ParametersUTRA-TDD-v1020			OPTIONAL,
	nonCriticalExtension				UE-EUTRA-Capability-v1060-IEs			OPTIONAL
}

UE-EUTRA-Capability-v1060-IEs ::=	SEQUENCE {
	fdd-Add-UE-EUTRA-Capabilities-v1060	UE-EUTRA-CapabilityAddXDD-Mode-v1060	OPTIONAL,
	tdd-Add-UE-EUTRA-Capabilities-v1060	UE-EUTRA-CapabilityAddXDD-Mode-v1060	OPTIONAL,
	rf-Parameters-v1060					RF-Parameters-v1060						OPTIONAL,
	nonCriticalExtension				UE-EUTRA-Capability-v1090-IEs			OPTIONAL
}

UE-EUTRA-Capability-v1090-IEs ::=	SEQUENCE {
	rf-Parameters-v1090					RF-Parameters-v1090						OPTIONAL,
	nonCriticalExtension				UE-EUTRA-Capability-v1130-IEs			OPTIONAL
}

UE-EUTRA-Capability-v1130-IEs ::=	SEQUENCE {
	pdcp-Parameters-v1130				PDCP-Parameters-v1130,
	phyLayerParameters-v1130			PhyLayerParameters-v1130				OPTIONAL,
	rf-Parameters-v1130					RF-Parameters-v1130,
	measParameters-v1130				MeasParameters-v1130,
	interRAT-ParametersCDMA2000-v1130	IRAT-ParametersCDMA2000-v1130,
	otherParameters-r11					Other-Parameters-r11,
	fdd-Add-UE-EUTRA-Capabilities-v1130	UE-EUTRA-CapabilityAddXDD-Mode-v1130	OPTIONAL,
	tdd-Add-UE-EUTRA-Capabilities-v1130	UE-EUTRA-CapabilityAddXDD-Mode-v1130	OPTIONAL,
	nonCriticalExtension				UE-EUTRA-Capability-v1170-IEs			OPTIONAL
}

UE-EUTRA-Capability-v1170-IEs ::=	SEQUENCE {
	phyLayerParameters-v1170			PhyLayerParameters-v1170				OPTIONAL,
	ue-Category-v1170					INTEGER (9..10)							OPTIONAL,
	nonCriticalExtension				UE-EUTRA-Capability-v1180-IEs			OPTIONAL
}

UE-EUTRA-Capability-v1180-IEs ::=	SEQUENCE {
	rf-Parameters-v1180					RF-Parameters-v1180						OPTIONAL,
	mbms-Parameters-r11					MBMS-Parameters-r11						OPTIONAL,
	fdd-Add-UE-EUTRA-Capabilities-v1180	UE-EUTRA-CapabilityAddXDD-Mode-v1180	OPTIONAL,
	tdd-Add-UE-EUTRA-Capabilities-v1180	UE-EUTRA-CapabilityAddXDD-Mode-v1180	OPTIONAL,
	nonCriticalExtension				UE-EUTRA-Capability-v11a0-IEs			OPTIONAL
}

UE-EUTRA-Capability-v11a0-IEs ::=	SEQUENCE {
	ue-Category-v11a0					INTEGER (11..12)						OPTIONAL,
	measParameters-v11a0				MeasParameters-v11a0					OPTIONAL,
	nonCriticalExtension				UE-EUTRA-Capability-v1250-IEs			OPTIONAL
}

UE-EUTRA-Capability-v1250-IEs ::=	SEQUENCE {
	phyLayerParameters-v1250			PhyLayerParameters-v1250				OPTIONAL,
	rf-Parameters-v1250					RF-Parameters-v1250						OPTIONAL,
	rlc-Parameters-r12					RLC-Parameters-r12						OPTIONAL,
	ue-BasedNetwPerfMeasParameters-v1250	UE-BasedNetwPerfMeasParameters-v1250	OPTIONAL,
	ue-CategoryDL-r12					INTEGER (0..14)							OPTIONAL,
	ue-CategoryUL-r12					INTEGER (0..13)							OPTIONAL,
	wlan-IW-Parameters-r12				WLAN-IW-Parameters-r12					OPTIONAL,
	measParameters-v1250				MeasParameters-v1250					OPTIONAL,
	dc-Parameters-r12					DC-Parameters-r12						OPTIONAL,
	mbms-Parameters-v1250				MBMS-Parameters-v1250					OPTIONAL,
	mac-Parameters-r12					MAC-Parameters-r12						OPTIONAL,
	fdd-Add-UE-EUTRA-Capabilities-v1250	UE-EUTRA-CapabilityAddXDD-Mode-v1250	OPTIONAL,
	tdd-Add-UE-EUTRA-Capabilities-v1250	UE-EUTRA-CapabilityAddXDD-Mode-v1250	OPTIONAL,
	sl-Parameters-r12				SL-Parameters-r12					OPTIONAL,
	nonCriticalExtension				UE-EUTRA-Capability-v1260-IEs			OPTIONAL
}

UE-EUTRA-Capability-v1260-IEs ::=	SEQUENCE {
	ue-CategoryDL-v1260					INTEGER (15..16)						OPTIONAL,
	nonCriticalExtension				UE-EUTRA-Capability-v1270-IEs			OPTIONAL
}

UE-EUTRA-Capability-v1270-IEs ::= SEQUENCE {
	rf-Parameters-v1270					RF-Parameters-v1270						OPTIONAL,
	nonCriticalExtension				UE-EUTRA-Capability-v1280-IEs			OPTIONAL
}

UE-EUTRA-Capability-v1280-IEs ::= SEQUENCE {
	phyLayerParameters-v1280			PhyLayerParameters-v1280				OPTIONAL,
	nonCriticalExtension				UE-EUTRA-Capability-v13x0-IEs 			OPTIONAL
}

UE-EUTRA-Capability-v13x0-IEs ::= SEQUENCE {
	dc-Parameters-v13x0					DC-Parameters-v13x0						OPTIONAL,
	measParameters-v13xy				MeasParameters-v13xy					OPTIONAL,
	mac-Parameters-v13x0				MAC-Parameters-v13x0					OPTIONAL,
	pdcp-Parameters-v13x0			PDCP-Parameters-v13x0				OPTIONAL,
	phyLayerParameters-v13x0			PhyLayerParameters-v13x0				OPTIONAL,
	rf-Parameters-v13x0				RF-Parameters-v13x0					OPTIONAL,
	rlc-Parameters-v13x0				RLC-Parameters-v13x0					OPTIONAL,
	ue-CategoryDL-v13x0				INTEGER (17)							OPTIONAL,
	ue-CategoryUL-v13x0				INTEGER (14)							OPTIONAL,
	scptm-Parameters-v13x0				SCPTM-Parameters-v13x0					OPTIONAL,
	sl-Parameters-r13				SL-Parameters-r13					OPTIONAL,
	supportOfLAA-r13					ENUMERATED {supported}					OPTIONAL,
	nonCriticalExtension				SEQUENCE {}							OPTIONAL
}

UE-EUTRA-CapabilityAddXDD-Mode-r9 ::=	SEQUENCE {
	phyLayerParameters-r9				PhyLayerParameters					OPTIONAL,
	featureGroupIndicators-r9			BIT STRING (SIZE (32))				OPTIONAL,
	featureGroupIndRel9Add-r9			BIT STRING (SIZE (32))				OPTIONAL,
	interRAT-ParametersGERAN-r9			IRAT-ParametersGERAN				OPTIONAL,
	interRAT-ParametersUTRA-r9			IRAT-ParametersUTRA-v920			OPTIONAL,
	interRAT-ParametersCDMA2000-r9		IRAT-ParametersCDMA2000-1XRTT-v920	OPTIONAL,
	neighCellSI-AcquisitionParameters-r9	NeighCellSI-AcquisitionParameters-r9	OPTIONAL,
	...
}

UE-EUTRA-CapabilityAddXDD-Mode-v1060 ::=	SEQUENCE {
	phyLayerParameters-v1060			PhyLayerParameters-v1020			OPTIONAL,
	featureGroupIndRel10-v1060			BIT STRING (SIZE (32))				OPTIONAL,
	interRAT-ParametersCDMA2000-v1060	IRAT-ParametersCDMA2000-1XRTT-v1020	OPTIONAL,
	interRAT-ParametersUTRA-TDD-v1060	IRAT-ParametersUTRA-TDD-v1020		OPTIONAL,
--	...,
	[[	otdoa-PositioningCapabilities-r10	OTDOA-PositioningCapabilities-r10	OPTIONAL
	]]
}

UE-EUTRA-CapabilityAddXDD-Mode-v1130 ::=	SEQUENCE {
	phyLayerParameters-v1130			PhyLayerParameters-v1130			OPTIONAL,
	measParameters-v1130				MeasParameters-v1130				OPTIONAL,
	otherParameters-r11					Other-Parameters-r11				OPTIONAL,
	...
}

UE-EUTRA-CapabilityAddXDD-Mode-v1180 ::=	SEQUENCE {
	mbms-Parameters-r11					MBMS-Parameters-r11
}

UE-EUTRA-CapabilityAddXDD-Mode-v1250 ::=	SEQUENCE {
	phyLayerParameters-v1250			PhyLayerParameters-v1250			OPTIONAL,
	measParameters-v1250				MeasParameters-v1250				OPTIONAL
}

AccessStratumRelease ::=			ENUMERATED {
										rel8, rel9, rel10, rel11, rel12, spare3,
										spare2, spare1, ...}

DC-Parameters-r12 ::=			SEQUENCE {
	drb-TypeSplit-r12						ENUMERATED {supported}			OPTIONAL,
	drb-TypeSCG-r12							ENUMERATED {supported}			OPTIONAL
}

DC-Parameters-v13x0 ::=			SEQUENCE {
	pdcp-TransferSplitUL-r13				ENUMERATED {supported}			OPTIONAL,
	ue-SSTD-Meas-r13						ENUMERATED {supported}			OPTIONAL
}

MAC-Parameters-r12 ::=				SEQUENCE {
	logicalChannelSR-ProhibitTimer-r12	ENUMERATED {supported}				OPTIONAL,
	longDRX-Command-r12				ENUMERATED {supported}					OPTIONAL
}

MAC-Parameters-v13x0 ::=				SEQUENCE {
	extendedMAC-LengthField-r13		ENUMERATED {supported}				OPTIONAL,
	extendedLongDRX-r13				ENUMERATED {supported}				OPTIONAL
}

RLC-Parameters-r12 ::=				SEQUENCE {
	extended-RLC-LI-Field-r12			ENUMERATED {supported}
}

RLC-Parameters-v13x0 ::=				SEQUENCE {
	extendedRLC-SN-SO-Field-r13				ENUMERATED {supported}
}

PDCP-Parameters ::=				SEQUENCE {
	supportedROHC-Profiles				SEQUENCE {
		profile0x0001						BOOLEAN,
		profile0x0002						BOOLEAN,
		profile0x0003						BOOLEAN,
		profile0x0004						BOOLEAN,
		profile0x0006						BOOLEAN,
		profile0x0101						BOOLEAN,
		profile0x0102						BOOLEAN,
		profile0x0103						BOOLEAN,
		profile0x0104						BOOLEAN
	},
	maxNumberROHC-ContextSessions		ENUMERATED {
											cs2, cs4, cs8, cs12, cs16, cs24, cs32,
											cs48, cs64, cs128, cs256, cs512, cs1024,
											cs16384, spare2, spare1}				DEFAULT cs16,
	...
}

PDCP-Parameters-v1130 ::=		SEQUENCE {
	pdcp-SN-Extension-r11					ENUMERATED {supported}			OPTIONAL,
	supportRohcContextContinue-r11			ENUMERATED {supported}			OPTIONAL
}

PDCP-Parameters-v13x0 ::=				SEQUENCE {
	pdcp-SN-Extension-18bits-r13			ENUMERATED {supported}
}

PhyLayerParameters ::=				SEQUENCE {
	ue-TxAntennaSelectionSupported		BOOLEAN,
	ue-SpecificRefSigsSupported		BOOLEAN
}

PhyLayerParameters-v920 ::=		SEQUENCE {
	enhancedDualLayerFDD-r9			ENUMERATED {supported}			OPTIONAL,
	enhancedDualLayerTDD-r9			ENUMERATED {supported}			OPTIONAL
}

PhyLayerParameters-v9d0 ::=			SEQUENCE {
	tm5-FDD-r9						ENUMERATED {supported}			OPTIONAL,
	tm5-TDD-r9						ENUMERATED {supported}			OPTIONAL
}

PhyLayerParameters-v1020 ::=			SEQUENCE {
	twoAntennaPortsForPUCCH-r10				ENUMERATED {supported}					OPTIONAL,
	tm9-With-8Tx-FDD-r10					ENUMERATED {supported}					OPTIONAL,
	pmi-Disabling-r10						ENUMERATED {supported}					OPTIONAL,
	crossCarrierScheduling-r10				ENUMERATED {supported}					OPTIONAL,
	simultaneousPUCCH-PUSCH-r10				ENUMERATED {supported}					OPTIONAL,
	multiClusterPUSCH-WithinCC-r10			ENUMERATED {supported}					OPTIONAL,
	nonContiguousUL-RA-WithinCC-List-r10	NonContiguousUL-RA-WithinCC-List-r10	OPTIONAL
}

PhyLayerParameters-v1130 ::=			SEQUENCE {
	crs-InterfHandl-r11						ENUMERATED {supported}					OPTIONAL,
	ePDCCH-r11								ENUMERATED {supported}					OPTIONAL,
	multiACK-CSI-Reporting-r11				ENUMERATED {supported}					OPTIONAL,
	ss-CCH-InterfHandl-r11					ENUMERATED {supported}					OPTIONAL,
	tdd-SpecialSubframe-r11					ENUMERATED {supported}					OPTIONAL,
	txDiv-PUCCH1b-ChSelect-r11				ENUMERATED {supported}					OPTIONAL,
	ul-CoMP-r11								ENUMERATED {supported}					OPTIONAL
}

PhyLayerParameters-v1170 ::=			SEQUENCE {
	interBandTDD-CA-WithDifferentConfig-r11	BIT STRING (SIZE (2))			OPTIONAL
}

PhyLayerParameters-v1250 ::=			SEQUENCE {
	e-HARQ-Pattern-FDD-r12					ENUMERATED {supported}			OPTIONAL,
	enhanced-4TxCodebook-r12				ENUMERATED {supported}			OPTIONAL,
	tdd-FDD-CA-PCellDuplex-r12				BIT STRING (SIZE (2))			OPTIONAL,
	phy-TDD-ReConfig-TDD-PCell-r12			ENUMERATED {supported}			OPTIONAL,
	phy-TDD-ReConfig-FDD-PCell-r12			ENUMERATED {supported}			OPTIONAL,
	pusch-FeedbackMode-r12					ENUMERATED {supported}			OPTIONAL,
	pusch-SRS-PowerControl-SubframeSet-r12	ENUMERATED {supported}			OPTIONAL,
	csi-SubframeSet-r12						ENUMERATED {supported}			OPTIONAL,
	noResourceRestrictionForTTIBundling-r12	ENUMERATED {supported}			OPTIONAL,
	discoverySignalsInDeactSCell-r12		ENUMERATED {supported}			OPTIONAL,
	naics-Capability-List-r12				NAICS-Capability-List-r12		OPTIONAL
}

PhyLayerParameters-v1280 ::=			SEQUENCE {
	alternativeTBS-Indices-r12				ENUMERATED {supported}			OPTIONAL
}
PhyLayerParameters-v13x0 ::=			SEQUENCE {
	codebook-HARQ-ACK-r13					BIT STRING (SIZE (2))			OPTIONAL,
	fdd-Harq-TimingTDD-r13					ENUMERATED {supported}			OPTIONAL,	maxNumberUpdatedCSI-Proc-r13				INTEGER(5..32)					OPTIONAL,
	supportedBlindDecoding-r13				INTEGER(1..32)					OPTIONAL,
	pucch-Format4-r13						ENUMERATED {supported}			OPTIONAL,
	pucch-Format5-r13						ENUMERATED {supported}			OPTIONAL,
	pucch-SCell-r13							ENUMERATED {supported}			OPTIONAL
}

NonContiguousUL-RA-WithinCC-List-r10 ::= SEQUENCE (SIZE (1..maxBands)) OF NonContiguousUL-RA-WithinCC-r10

NonContiguousUL-RA-WithinCC-r10 ::=		SEQUENCE {
	nonContiguousUL-RA-WithinCC-Info-r10	ENUMERATED {supported}					OPTIONAL
}

RF-Parameters ::=					SEQUENCE {
	supportedBandListEUTRA				SupportedBandListEUTRA
}

RF-Parameters-v9e0 ::=					SEQUENCE {
	supportedBandListEUTRA-v9e0				SupportedBandListEUTRA-v9e0				OPTIONAL
}

RF-Parameters-v1020 ::=				SEQUENCE {
	supportedBandCombination-r10			SupportedBandCombination-r10
}

RF-Parameters-v1060 ::=				SEQUENCE {
	supportedBandCombinationExt-r10			SupportedBandCombinationExt-r10
}

RF-Parameters-v1090 ::=					SEQUENCE {
	supportedBandCombination-v1090			SupportedBandCombination-v1090			OPTIONAL
}

RF-Parameters-v10f0 ::=					SEQUENCE {
	modifiedMPR-Behavior-r10					BIT STRING (SIZE (32))				OPTIONAL
}

RF-Parameters-v10i0 ::=					SEQUENCE {
	supportedBandCombination-v10i0			SupportedBandCombination-v10i0			OPTIONAL
}

RF-Parameters-v10j0 ::=					SEQUENCE {
	multiNS-Pmax-r10						ENUMERATED {supported}					OPTIONAL
}

RF-Parameters-v1130 ::=				SEQUENCE {
	supportedBandCombination-v1130			SupportedBandCombination-v1130			OPTIONAL
}

RF-Parameters-v1180 ::=				SEQUENCE {
	freqBandRetrieval-r11					ENUMERATED {supported}			OPTIONAL,
	requestedBands-r11						SEQUENCE (SIZE (1.. maxBands)) OF FreqBandIndicator-r11						OPTIONAL,
	supportedBandCombinationAdd-r11			SupportedBandCombinationAdd-r11		OPTIONAL
}

RF-Parameters-v11d0 ::=					SEQUENCE {
	supportedBandCombinationAdd-v11d0		SupportedBandCombinationAdd-v11d0		OPTIONAL
}

RF-Parameters-v1250 ::=				SEQUENCE {
	supportedBandListEUTRA-v1250				SupportedBandListEUTRA-v1250		OPTIONAL,
	supportedBandCombination-v1250			SupportedBandCombination-v1250			OPTIONAL,
	supportedBandCombinationAdd-v1250		SupportedBandCombinationAdd-v1250		OPTIONAL,
	freqBandPriorityAdjustment-r12			ENUMERATED {supported}					OPTIONAL
}

RF-Parameters-v1270 ::=				SEQUENCE {
	supportedBandCombination-v1270			SupportedBandCombination-v1270			OPTIONAL,
	supportedBandCombinationAdd-v1270		SupportedBandCombinationAdd-v1270		OPTIONAL
}

RF-Parameters-v13x0 ::=				SEQUENCE {
	requestedMaximumCCs-r13					ENUMERATED {supported, includedUL,
													includedDL, includedBoth}		OPTIONAL,
	skipFallbackCombinations-r13				ENUMERATED {supported, included}				OPTIONAL,
	supportedBandCombinations-r13		SupportedBandCombinations-r13				OPTIONAL, 
	supportedMIMO-CapabilityDL-r13		MIMO-CapabilityDL-r10						OPTIONAL
}
SupportedBandCombination-r10 ::= SEQUENCE (SIZE (1..maxBandComb-r10)) OF BandCombinationParameters-r10 

SupportedBandCombinationExt-r10 ::= SEQUENCE (SIZE (1..maxBandComb-r10)) OF BandCombinationParametersExt-r10

SupportedBandCombination-v1090 ::= SEQUENCE (SIZE (1..maxBandComb-r10)) OF BandCombinationParameters-v1090

SupportedBandCombination-v10i0 ::= SEQUENCE (SIZE (1..maxBandComb-r10)) OF BandCombinationParameters-v10i0

SupportedBandCombination-v1130 ::= SEQUENCE (SIZE (1..maxBandComb-r10)) OF BandCombinationParameters-v1130

SupportedBandCombination-v1250 ::= SEQUENCE (SIZE (1..maxBandComb-r10)) OF BandCombinationParameters-v1250

SupportedBandCombination-v1270 ::= SEQUENCE (SIZE (1..maxBandComb-r10)) OF BandCombinationParameters-v1270

SupportedBandCombinationAdd-r11 ::= SEQUENCE (SIZE (1..maxBandComb-r11)) OF BandCombinationParameters-r11

SupportedBandCombinationAdd-v11d0 ::= SEQUENCE (SIZE (1..maxBandComb-r11)) OF BandCombinationParameters-v10i0

SupportedBandCombinationAdd-v1250 ::= SEQUENCE (SIZE (1..maxBandComb-r11)) OF BandCombinationParameters-v1250

SupportedBandCombinationAdd-v1270 ::= SEQUENCE (SIZE (1..maxBandComb-r11)) OF BandCombinationParameters-v1270



SupportedBandCombinations-r13 ::=	SEQUENCE {
	bandCombinationList-r13						BandCombinationList-r13
}

BandCombinationList-r13 ::= SEQUENCE (SIZE (maxBandComb-r13)) OF BandCombination-r13

BandCombination-r13 ::=		SEQUENCE {
	additionalFallbackSupported-r13		ENUMERATED {true}				OPTIONAL,
	bandCombinationParameters-r13		BandCombinationParametersCommon-r13
}

BandCombinationParametersCommon-r13 ::= SEQUENCE {
	bandParameterList-r13			SEQUENCE (SIZE (1..maxSimultaneousBands-r10)) OF BandParameters-r13,
	supportedBandwidthCombinationSet-r13		SupportedBandwidthCombinationSet-r10		OPTIONAL,
	multipleTimingAdvance-r13		ENUMERATED {supported}					OPTIONAL,
	simultaneousRx-Tx-r13			ENUMERATED {supported}					OPTIONAL,
	bandInfoEUTRA-r13				BandInfoEUTRA,
	dc-Support-r13					SEQUENCE {
		asynchronous-r13			ENUMERATED {supported}			OPTIONAL,
		supportedCellGrouping-r13		CHOICE {
				threeEntries-r13				BIT STRING (SIZE(3)),
				fourEntries-r13					BIT STRING (SIZE(7)),
				fiveEntries-r13					BIT STRING (SIZE(15))
		}																OPTIONAL
	}																	OPTIONAL,
	supportedNAICS-2CRS-AP-r13		BIT STRING (SIZE (1..maxNAICS-Entries-r12))		OPTIONAL,
	commSupportedBandsPerBC-r13		BIT STRING (SIZE (1.. maxBands))		OPTIONAL
}


BandCombinationParameters-r10 ::= SEQUENCE (SIZE (1..maxSimultaneousBands-r10)) OF BandParameters-r10

BandCombinationParametersExt-r10 ::= SEQUENCE {
	supportedBandwidthCombinationSet-r10	SupportedBandwidthCombinationSet-r10	OPTIONAL
}

BandCombinationParameters-v1090 ::= SEQUENCE (SIZE (1..maxSimultaneousBands-r10)) OF BandParameters-v1090

BandCombinationParameters-v10i0::= SEQUENCE {
bandParameterList-v10i0			SEQUENCE (SIZE (1..maxSimultaneousBands-r10)) OF 
			BandParameters-v10i0	OPTIONAL
}

BandCombinationParameters-v1130 ::=	SEQUENCE {
	multipleTimingAdvance-r11		ENUMERATED {supported}					OPTIONAL,
	simultaneousRx-Tx-r11			ENUMERATED {supported}					OPTIONAL,
	bandParameterList-r11			SEQUENCE (SIZE (1..maxSimultaneousBands-r10)) OF BandParameters-v1130	OPTIONAL,
	...
}

BandCombinationParameters-r11 ::=	SEQUENCE {
	bandParameterList-r11			SEQUENCE (SIZE (1..maxSimultaneousBands-r10)) OF 
			BandParameters-r11,
	supportedBandwidthCombinationSet-r11	SupportedBandwidthCombinationSet-r10	OPTIONAL,
	multipleTimingAdvance-r11		ENUMERATED {supported}					OPTIONAL,
	simultaneousRx-Tx-r11			ENUMERATED {supported}					OPTIONAL,
	bandInfoEUTRA-r11				BandInfoEUTRA,
	...
}

BandCombinationParameters-v1250::= SEQUENCE {
	dc-Support-r12					SEQUENCE {
		asynchronous-r12				ENUMERATED {supported}			OPTIONAL,
		supportedCellGrouping-r12		CHOICE {
				threeEntries-r12				BIT STRING (SIZE(3)),
				fourEntries-r12					BIT STRING (SIZE(7)),
				fiveEntries-r12					BIT STRING (SIZE(15))
		}																OPTIONAL
	}																	OPTIONAL,
	supportedNAICS-2CRS-AP-r12		BIT STRING (SIZE (1..maxNAICS-Entries-r12))		OPTIONAL,
	commSupportedBandsPerBC-r12				BIT STRING (SIZE (1.. maxBands))		OPTIONAL,
	...
}

BandCombinationParameters-v1270 ::= SEQUENCE {
	bandParameterList-v1270			SEQUENCE (SIZE (1..maxSimultaneousBands-r10)) OF 
			BandParameters-v1270		OPTIONAL
}


SupportedBandwidthCombinationSet-r10 ::=	BIT STRING (SIZE (1..maxBandwidthCombSet-r10))

BandParameters-r10 ::= SEQUENCE {
	bandEUTRA-r10					FreqBandIndicator,
	bandParametersUL-r10			BandParametersUL-r10					OPTIONAL,
	bandParametersDL-r10			BandParametersDL-r10					OPTIONAL
}

BandParameters-v1090 ::= SEQUENCE {
	bandEUTRA-v1090					FreqBandIndicator-v9e0					OPTIONAL,
	...
}

BandParameters-v10i0::= SEQUENCE {
	bandParametersDL-v10i0		SEQUENCE (SIZE (1..maxBandwidthClass-r10)) OF CA-MIMO-ParametersDL-v10i0
}

BandParameters-v1130 ::= SEQUENCE {
	supportedCSI-Proc-r11			ENUMERATED {n1, n3, n4}
}

BandParameters-r11 ::= SEQUENCE {
	bandEUTRA-r11					FreqBandIndicator-r11,
	bandParametersUL-r11			BandParametersUL-r10					OPTIONAL,
	bandParametersDL-r11			BandParametersDL-r10					OPTIONAL,
	supportedCSI-Proc-r11			ENUMERATED {n1, n3, n4}					OPTIONAL
}

BandParameters-v1270 ::= SEQUENCE {
	bandParametersDL-v1270			SEQUENCE (SIZE (1..maxBandwidthClass-r10)) OF CA-MIMO-ParametersDL-v1270
}

BandParameters-r13 ::= SEQUENCE {
	bandEUTRA-r13					FreqBandIndicator-r11,
	bandParametersUL-r13				BandParametersUL-r13				OPTIONAL,
	bandParametersDL-r13				BandParametersDL-r13				OPTIONAL,
	supportedCSI-Proc-r13			ENUMERATED {n1, n3, n4}			OPTIONAL
}

BandParametersUL-r10 ::= SEQUENCE (SIZE (1..maxBandwidthClass-r10)) OF CA-MIMO-ParametersUL-r10

BandParametersUL-r13 ::= SEQUENCE OF CA-MIMO-ParametersUL-r10


CA-MIMO-ParametersUL-r10 ::= SEQUENCE {
	ca-BandwidthClassUL-r10				CA-BandwidthClass-r10,
	supportedMIMO-CapabilityUL-r10		MIMO-CapabilityUL-r10				OPTIONAL
}

BandParametersDL-r10 ::= SEQUENCE (SIZE (1..maxBandwidthClass-r10)) OF CA-MIMO-ParametersDL-r10

BandParametersDL-r13 ::= SEQUENCE OF CA-MIMO-ParametersDL-r13

CA-MIMO-ParametersDL-r10 ::= SEQUENCE {
	ca-BandwidthClassDL-r10				CA-BandwidthClass-r10,
	supportedMIMO-CapabilityDL-r10		MIMO-CapabilityDL-r10				OPTIONAL
}

CA-MIMO-ParametersDL-v10i0 ::= SEQUENCE {
	fourLayerTM3-TM4-r10				ENUMERATED {supported}				OPTIONAL
}

CA-MIMO-ParametersDL-v1270 ::= SEQUENCE {
	intraBandContiguousCC-InfoList-r12			SEQUENCE (SIZE (1..maxServCell-r10)) OF IntraBandContiguousCC-Info-r12
}

CA-MIMO-ParametersDL-r13 ::= SEQUENCE {
	ca-BandwidthClassDL-r13					CA-BandwidthClass-r10,
	supportedMIMO-CapabilityDL-r13			MIMO-CapabilityDL-r10				OPTIONAL,
	fourLayerTM3-TM4-r13						ENUMERATED {supported}				OPTIONAL,
	intraBandContiguousCC-InfoList-r13		SEQUENCE (SIZE (1..maxServCell-r13)) OF IntraBandContiguousCC-Info-r12
}

IntraBandContiguousCC-Info-r12 ::= SEQUENCE {
	fourLayerTM3-TM4-perCC-r12			ENUMERATED {supported}				OPTIONAL,
	supportedMIMO-CapabilityDL-r12		MIMO-CapabilityDL-r10				OPTIONAL,
	supportedCSI-Proc-r12				ENUMERATED {n1, n3, n4}				OPTIONAL
}

CA-BandwidthClass-r10 ::= ENUMERATED {a, b, c, d, e, f, ...}

MIMO-CapabilityUL-r10 ::= ENUMERATED {twoLayers, fourLayers}

MIMO-CapabilityDL-r10 ::= ENUMERATED {twoLayers, fourLayers, eightLayers}

SupportedBandListEUTRA ::=			SEQUENCE (SIZE (1..maxBands)) OF SupportedBandEUTRA 

SupportedBandListEUTRA-v9e0::=			SEQUENCE (SIZE (1..maxBands)) OF SupportedBandEUTRA-v9e0

SupportedBandListEUTRA-v1250 ::=		SEQUENCE (SIZE (1..maxBands)) OF SupportedBandEUTRA-v1250

SupportedBandEUTRA ::=				SEQUENCE {
	bandEUTRA							FreqBandIndicator,
	halfDuplex							BOOLEAN
}

SupportedBandEUTRA-v9e0 ::=		SEQUENCE {
	bandEUTRA-v9e0						FreqBandIndicator-v9e0		OPTIONAL
}

SupportedBandEUTRA-v1250 ::=		SEQUENCE {
	dl-256QAM-r12						ENUMERATED {supported}		OPTIONAL,
	ul-64QAM-r12						ENUMERATED {supported}		OPTIONAL
}

MeasParameters ::=					SEQUENCE {
	bandListEUTRA						BandListEUTRA
}

MeasParameters-v1020 ::=			SEQUENCE {
	bandCombinationListEUTRA-r10			BandCombinationListEUTRA-r10
}

MeasParameters-v1130 ::=			SEQUENCE {
	rsrqMeasWideband-r11			ENUMERATED {supported}					OPTIONAL
}

MeasParameters-v11a0 ::=			SEQUENCE {
	benefitsFromInterruption-r11			ENUMERATED {true}				OPTIONAL
}

MeasParameters-v1250 ::=			SEQUENCE {	
	timerT312-r12						ENUMERATED {supported}		OPTIONAL,
	alternativeTimeToTrigger-r12		ENUMERATED {supported}		OPTIONAL,
	incMonEUTRA-r12						ENUMERATED {supported}		OPTIONAL,
	incMonUTRA-r12						ENUMERATED {supported}		OPTIONAL,
	extendedMaxMeasId-r12				ENUMERATED {supported}		OPTIONAL,
	extendedRSRQ-LowerRange-r12			ENUMERATED {supported}		OPTIONAL,
	rsrq-OnAllSymbols-r12				ENUMERATED {supported}		OPTIONAL,
	crs-DiscoverySignalsMeas-r12		ENUMERATED {supported}		OPTIONAL,
	csi-RS-DiscoverySignalsMeas-r12		ENUMERATED {supported}		OPTIONAL
}

MeasParameters-v13xy ::=			SEQUENCE {
	rs-SINR-Meas-r13					ENUMERATED {supported}		OPTIONAL,
	whiteCellList-r13		ENUMERATED {supported}		OPTIONAL
}

BandListEUTRA ::=					SEQUENCE (SIZE (1..maxBands)) OF BandInfoEUTRA 

BandCombinationListEUTRA-r10 ::=	SEQUENCE (SIZE (1..maxBandComb-r10)) OF BandInfoEUTRA

BandInfoEUTRA ::=					SEQUENCE {
	interFreqBandList					InterFreqBandList,
	interRAT-BandList					InterRAT-BandList		OPTIONAL
}

InterFreqBandList ::=				SEQUENCE (SIZE (1..maxBands)) OF InterFreqBandInfo

InterFreqBandInfo ::=				SEQUENCE {
	interFreqNeedForGaps				BOOLEAN
}

InterRAT-BandList ::=				SEQUENCE (SIZE (1..maxBands)) OF InterRAT-BandInfo

InterRAT-BandInfo ::=				SEQUENCE {
	interRAT-NeedForGaps				BOOLEAN
}

IRAT-ParametersUTRA-FDD ::=		SEQUENCE {
	supportedBandListUTRA-FDD			SupportedBandListUTRA-FDD
}

IRAT-ParametersUTRA-v920 ::=		SEQUENCE {
	e-RedirectionUTRA-r9				ENUMERATED {supported}
}

IRAT-ParametersUTRA-v9c0 ::=		SEQUENCE {
	voiceOverPS-HS-UTRA-FDD-r9						ENUMERATED {supported}		OPTIONAL,
	voiceOverPS-HS-UTRA-TDD128-r9					ENUMERATED {supported}		OPTIONAL,
	srvcc-FromUTRA-FDD-ToUTRA-FDD-r9				ENUMERATED {supported}		OPTIONAL,
	srvcc-FromUTRA-FDD-ToGERAN-r9					ENUMERATED {supported}		OPTIONAL,
	srvcc-FromUTRA-TDD128-ToUTRA-TDD128-r9			ENUMERATED {supported}		OPTIONAL,
	srvcc-FromUTRA-TDD128-ToGERAN-r9				ENUMERATED {supported}		OPTIONAL
}

IRAT-ParametersUTRA-v9h0 ::=		SEQUENCE {
	mfbi-UTRA-r9						ENUMERATED {supported}
}

SupportedBandListUTRA-FDD ::=		SEQUENCE (SIZE (1..maxBands)) OF SupportedBandUTRA-FDD 

SupportedBandUTRA-FDD ::=			ENUMERATED {
										bandI, bandII, bandIII, bandIV, bandV, bandVI,
										bandVII, bandVIII, bandIX, bandX, bandXI,
										bandXII, bandXIII, bandXIV, bandXV, bandXVI, ...,
										bandXVII-8a0, bandXVIII-8a0, bandXIX-8a0, bandXX-8a0,
										bandXXI-8a0, bandXXII-8a0, bandXXIII-8a0, bandXXIV-8a0,
										bandXXV-8a0, bandXXVI-8a0, bandXXVII-8a0, bandXXVIII-8a0,
										bandXXIX-8a0, bandXXX-8a0, bandXXXI-8a0, bandXXXII-8a0}

IRAT-ParametersUTRA-TDD128 ::=		SEQUENCE {
	supportedBandListUTRA-TDD128		SupportedBandListUTRA-TDD128
}

SupportedBandListUTRA-TDD128 ::=	SEQUENCE (SIZE (1..maxBands)) OF SupportedBandUTRA-TDD128 

SupportedBandUTRA-TDD128 ::=		ENUMERATED {
										a, b, c, d, e, f, g, h, i, j, k, l, m, n,
										o, p, ...}

IRAT-ParametersUTRA-TDD384 ::=		SEQUENCE {
	supportedBandListUTRA-TDD384		SupportedBandListUTRA-TDD384
}

SupportedBandListUTRA-TDD384 ::=	SEQUENCE (SIZE (1..maxBands)) OF SupportedBandUTRA-TDD384 

SupportedBandUTRA-TDD384 ::=		ENUMERATED {
											a, b, c, d, e, f, g, h, i, j, k, l, m, n,
											o, p, ...}

IRAT-ParametersUTRA-TDD768 ::=		SEQUENCE {
	supportedBandListUTRA-TDD768		SupportedBandListUTRA-TDD768
}

SupportedBandListUTRA-TDD768 ::=	SEQUENCE (SIZE (1..maxBands)) OF SupportedBandUTRA-TDD768 

SupportedBandUTRA-TDD768 ::=		ENUMERATED {
										a, b, c, d, e, f, g, h, i, j, k, l, m, n,
										o, p, ...}

IRAT-ParametersUTRA-TDD-v1020 ::=		SEQUENCE {
	e-RedirectionUTRA-TDD-r10				ENUMERATED {supported}
}

IRAT-ParametersGERAN ::=			SEQUENCE {
	supportedBandListGERAN				SupportedBandListGERAN,
	interRAT-PS-HO-ToGERAN				BOOLEAN
}

IRAT-ParametersGERAN-v920 ::=		SEQUENCE {
	dtm-r9								ENUMERATED {supported}			OPTIONAL,
	e-RedirectionGERAN-r9				ENUMERATED {supported}			OPTIONAL
}

SupportedBandListGERAN ::=			SEQUENCE (SIZE (1..maxBands)) OF SupportedBandGERAN 

SupportedBandGERAN ::=				ENUMERATED {
										gsm450, gsm480, gsm710, gsm750, gsm810, gsm850,
										gsm900P, gsm900E, gsm900R, gsm1800, gsm1900,
										spare5, spare4, spare3, spare2, spare1, ...}

IRAT-ParametersCDMA2000-HRPD ::=	SEQUENCE {
	supportedBandListHRPD				SupportedBandListHRPD,
	tx-ConfigHRPD						ENUMERATED {single, dual},
	rx-ConfigHRPD						ENUMERATED {single, dual}
}

SupportedBandListHRPD ::=			SEQUENCE (SIZE (1..maxCDMA-BandClass)) OF BandclassCDMA2000

IRAT-ParametersCDMA2000-1XRTT ::=	SEQUENCE {
	supportedBandList1XRTT				SupportedBandList1XRTT,
	tx-Config1XRTT						ENUMERATED {single, dual},
	rx-Config1XRTT						ENUMERATED {single, dual}
}

IRAT-ParametersCDMA2000-1XRTT-v920 ::=	SEQUENCE {
	e-CSFB-1XRTT-r9						ENUMERATED {supported},
	e-CSFB-ConcPS-Mob1XRTT-r9			ENUMERATED {supported}			OPTIONAL
}

IRAT-ParametersCDMA2000-1XRTT-v1020 ::=	SEQUENCE {
	e-CSFB-dual-1XRTT-r10				ENUMERATED {supported}
}

IRAT-ParametersCDMA2000-v1130 ::=		SEQUENCE {
	cdma2000-NW-Sharing-r11					ENUMERATED {supported}		OPTIONAL
}

SupportedBandList1XRTT ::=			SEQUENCE (SIZE (1..maxCDMA-BandClass)) OF BandclassCDMA2000

CSG-ProximityIndicationParameters-r9 ::=	SEQUENCE {
	intraFreqProximityIndication-r9	ENUMERATED {supported}			OPTIONAL,
	interFreqProximityIndication-r9	ENUMERATED {supported}			OPTIONAL,
	utran-ProximityIndication-r9		ENUMERATED {supported}			OPTIONAL
}

NeighCellSI-AcquisitionParameters-r9 ::=	SEQUENCE {
	intraFreqSI-AcquisitionForHO-r9	ENUMERATED {supported}			OPTIONAL,
	interFreqSI-AcquisitionForHO-r9	ENUMERATED {supported}			OPTIONAL,
	utran-SI-AcquisitionForHO-r9		ENUMERATED {supported}			OPTIONAL
}

SON-Parameters-r9 ::=				SEQUENCE {
	rach-Report-r9						ENUMERATED {supported}			OPTIONAL
}

UE-BasedNetwPerfMeasParameters-r10 ::=	SEQUENCE {
	loggedMeasurementsIdle-r10				ENUMERATED {supported}		OPTIONAL,
	standaloneGNSS-Location-r10				ENUMERATED {supported}		OPTIONAL
}

UE-BasedNetwPerfMeasParameters-v1250 ::= 	SEQUENCE {
	loggedMBSFNMeasurements-r12				ENUMERATED {supported}
}

OTDOA-PositioningCapabilities-r10 ::=	SEQUENCE {
	otdoa-UE-Assisted-r10					ENUMERATED {supported},
	interFreqRSTD-Measurement-r10			ENUMERATED {supported}		OPTIONAL
}

Other-Parameters-r11 ::=				SEQUENCE {
	inDeviceCoexInd-r11						ENUMERATED {supported}		OPTIONAL,
	powerPrefInd-r11						ENUMERATED {supported}		OPTIONAL,
	ue-Rx-TxTimeDiffMeasurements-r11		ENUMERATED {supported}		OPTIONAL
}

Other-Parameters-v11d0 ::=				SEQUENCE {
	inDeviceCoexInd-UL-CA-r11				ENUMERATED {supported}		OPTIONAL
}

MBMS-Parameters-r11 ::=				SEQUENCE {
	mbms-SCell-r11							ENUMERATED {supported}		OPTIONAL,
	mbms-NonServingCell-r11					ENUMERATED {supported}		OPTIONAL
}

MBMS-Parameters-v1250 ::=				SEQUENCE {
	mbms-AsyncDC-r12						ENUMERATED {supported}		OPTIONAL
}

SCPTM-Parameters-v13x0 ::=				SEQUENCE {
	scptm-ParallelReception-r13					ENUMERATED {supported}		OPTIONAL
}

WLAN-IW-Parameters-r12 ::=	SEQUENCE {
	wlan-IW-RAN-Rules-r12					ENUMERATED {supported}		OPTIONAL,
	wlan-IW-ANDSF-Policies-r12						ENUMERATED {supported}		OPTIONAL
}

NAICS-Capability-List-r12 ::= SEQUENCE (SIZE (1..maxNAICS-Entries-r12)) OF NAICS-Capability-Entry-r12


NAICS-Capability-Entry-r12	::=	SEQUENCE {
	numberOfNAICS-CapableCC-r12				INTEGER(1..5),
	numberOfAggregatedPRB-r12				ENUMERATED {
												n50, n75, n100, n125, n150, n175, 
												n200, n225, n250, n275, n300, n350,
												n400, n450, n500, spare},
	...
}

SL-Parameters-r12 ::=				SEQUENCE {
	commSimultaneousTx-r12					ENUMERATED {supported}		OPTIONAL,
	commSupportedBands-r12					FreqBandIndicatorListEUTRA-r12 	OPTIONAL,
	discSupportedBands-r12					SupportedBandInfoList-r12 	OPTIONAL,
	discScheduledResourceAlloc-r12			ENUMERATED {supported}		OPTIONAL,
	disc-UE-SelectedResourceAlloc-r12		ENUMERATED {supported}		OPTIONAL,
	disc-SLSS-r12							ENUMERATED {supported}		OPTIONAL,
	discSupportedProc-r12					ENUMERATED {n50, n400}		OPTIONAL
}

SL-Parameters-r13 ::=				SEQUENCE {
	discSysInfoReporting-r13					ENUMERATED {supported}		OPTIONAL
}

SupportedBandInfoList-r12 ::=		SEQUENCE (SIZE (1..maxBands)) OF SupportedBandInfo-r12 

SupportedBandInfo-r12 ::=			SEQUENCE {
	support-r12								ENUMERATED {supported}	OPTIONAL
}

FreqBandIndicatorListEUTRA-r12 ::=		SEQUENCE (SIZE (1..maxBands)) OF FreqBandIndicator-r11

-- ASN1STOP

UE-RadioPagingInfo-r12 ::=				SEQUENCE {
	ue-Category-v1250					INTEGER (0)			OPTIONAL,
	...
}

-- ASN1STOP

UE-TimersAndConstants ::=			SEQUENCE {
	t300								ENUMERATED {
											ms100, ms200, ms300, ms400, ms600, ms1000, ms1500,
											ms2000},
	t301								ENUMERATED {
											ms100, ms200, ms300, ms400, ms600, ms1000, ms1500,
											ms2000},
	t310								ENUMERATED {
											ms0, ms50, ms100, ms200, ms500, ms1000, ms2000},
	n310								ENUMERATED {
											n1, n2, n3, n4, n6, n8, n10, n20},
	t311								ENUMERATED {
											ms1000, ms3000, ms5000, ms10000, ms15000,
											ms20000, ms30000},
	n311								ENUMERATED {
											n1, n2, n3, n4, n5, n6, n8, n10},
	...
}

-- ASN1STOP

VisitedCellInfoList-r12 ::=	SEQUENCE (SIZE (1..maxCellHistory-r12)) OF VisitedCellInfo-r12

VisitedCellInfo-r12 ::=				SEQUENCE {
	visitedCellId-r12					CHOICE {
		cellGlobalId-r12						CellGlobalIdEUTRA,
		pci-arfcn-r12							SEQUENCE {
			physCellId-r12							PhysCellId,
			carrierFreq-r12							ARFCN-ValueEUTRA-r9
		}
	}																OPTIONAL,
	timeSpent-r12						INTEGER (0..4095),
	...
}

-- ASN1STOP

WLAN-OffloadConfig-r12 ::= 				SEQUENCE {
	thresholdRSRP-r12						SEQUENCE {
		thresholdRSRP-Low-r12					RSRP-Range,
		thresholdRSRP-High-r12					RSRP-Range
	}																	OPTIONAL, -- Need OR
	thresholdRSRQ-r12						SEQUENCE {
		thresholdRSRQ-Low-r12					RSRQ-Range,
		thresholdRSRQ-High-r12					RSRQ-Range
	}																	OPTIONAL, -- Need OR
	thresholdRSRQ-OnAllSymbolsWithWB-r12	SEQUENCE {
		thresholdRSRQ-OnAllSymbolsWithWB-Low-r12			RSRQ-Range,
		thresholdRSRQ-OnAllSymbolsWithWB-High-r12			RSRQ-Range
	}																	OPTIONAL, -- Need OP
	thresholdRSRQ-OnAllSymbols-r12			SEQUENCE {
			thresholdRSRQ-OnAllSymbolsLow-r12					RSRQ-Range,
			thresholdRSRQ-OnAllSymbolsHigh-r12					RSRQ-Range
	}																	OPTIONAL, -- Need OP
	thresholdRSRQ-WB-r12					SEQUENCE {
		thresholdRSRQ-WB-Low-r12							RSRQ-Range,
		thresholdRSRQ-WB-High-r12							RSRQ-Range
	}																	OPTIONAL, -- Need OP

	thresholdChannelUtilization-r12			SEQUENCE {
		thresholdChannelUtilizationLow-r12		INTEGER (0..255),
		thresholdChannelUtilizationHigh-r12		INTEGER (0..255)
	}																	OPTIONAL, -- Need OR
	thresholdBackhaul-Bandwidth-r12			SEQUENCE {
		thresholdBackhaulDL-BandwidthLow-r12	WLAN-backhaulRate-r12,
		thresholdBackhaulDL-BandwidthHigh-r12	WLAN-backhaulRate-r12,
		thresholdBackhaulUL-BandwidthLow-r12	WLAN-backhaulRate-r12,
	 	thresholdBackhaulUL-BandwidthHigh-r12	WLAN-backhaulRate-r12
	}																	OPTIONAL, -- Need OR
	thresholdBeaconRSSI-r12						SEQUENCE {
		thresholdBeaconRSSI-Low-r12					INTEGER (0..255),
		thresholdBeaconRSSI-High-r12					INTEGER (0..255)
	}																	OPTIONAL, -- Need OR
	offloadPreferenceIndicator-r12			BIT STRING (SIZE (16))		OPTIONAL, -- Need OR
	t-SteeringWLAN-r12						T-Reselection				OPTIONAL, -- Need OR
	...
}

WLAN-backhaulRate-r12 ::=					ENUMERATED
										 {r0, r4, r8, r16, r32, r64, r128, r256, r512,
										 r1024, r2048, r4096, r8192, r16384, r32768, r65536, r131072,
										 r262144, r524288, r1048576, r2097152, r4194304, r8388608,
										 r16777216, r33554432, r67108864, r134217728, r268435456,
										 r536870912, r1073741824, r2147483648, r4294967296}

-- ASN1STOP

MBMS-NotificationConfig-r9 ::=				SEQUENCE {
	notificationRepetitionCoeff-r9		ENUMERATED {n2, n4},
	notificationOffset-r9				INTEGER (0..10),
	notificationSF-Index-r9				INTEGER (1..6)
}

-- ASN1STOP

MBMSServiceList-r13 ::=			SEQUENCE (SIZE (0..maxMBMSServiceListPerUE-r13)) OF MBMSServiceInfo-r13

MBMSServiceInfo-r13 ::= 				SEQUENCE	{
	tmgi-r13							TMGI-r9
}

-- ASN1STOP

MBSFN-AreaId-r12 ::=					INTEGER (0..255)

-- ASN1STOP

MBSFN-AreaInfoList-r9 ::=			SEQUENCE (SIZE(1..maxMBSFN-Area)) OF MBSFN-AreaInfo-r9

MBSFN-AreaInfo-r9 ::=				SEQUENCE {
	mbsfn-AreaId-r9						MBSFN-AreaId-r12,
	non-MBSFNregionLength				ENUMERATED {s1, s2},
	notificationIndicator-r9				INTEGER (0..7),
	mcch-Config-r9						SEQUENCE {
		mcch-RepetitionPeriod-r9			ENUMERATED {rf32, rf64, rf128, rf256},
		mcch-Offset-r9						INTEGER (0..10),
		mcch-ModificationPeriod-r9			ENUMERATED {rf512, rf1024},
		sf-AllocInfo-r9						BIT STRING (SIZE(6)),
		signallingMCS-r9					ENUMERATED {n2, n7, n13, n19}
	},
	...
}

-- ASN1STOP

MBSFN-SubframeConfig ::=			SEQUENCE {
	radioframeAllocationPeriod			ENUMERATED {n1, n2, n4, n8, n16, n32},
	radioframeAllocationOffset			INTEGER (0..7),
	subframeAllocation					CHOICE {
		oneFrame							BIT STRING (SIZE(6)),
		fourFrames							BIT STRING (SIZE(24))
	}
}
-- ASN1STOP

PMCH-InfoList-r9 ::=				SEQUENCE (SIZE (0..maxPMCH-PerMBSFN)) OF PMCH-Info-r9

PMCH-InfoListExt-r12 ::=			SEQUENCE (SIZE (0..maxPMCH-PerMBSFN)) OF PMCH-InfoExt-r12

PMCH-Info-r9 ::=					SEQUENCE {
	pmch-Config-r9						PMCH-Config-r9,
	mbms-SessionInfoList-r9			MBMS-SessionInfoList-r9,
	...
}

PMCH-InfoExt-r12 ::=				SEQUENCE {
	pmch-Config-r12						PMCH-Config-r12,
	mbms-SessionInfoList-r12			MBMS-SessionInfoList-r9,
	...
}

MBMS-SessionInfoList-r9 ::=		SEQUENCE (SIZE (0..maxSessionPerPMCH)) OF MBMS-SessionInfo-r9

MBMS-SessionInfo-r9 ::=			SEQUENCE {
	tmgi-r9								TMGI-r9,
	sessionId-r9						OCTET STRING (SIZE (1)) 		OPTIONAL, 	-- Need OR
	logicalChannelIdentity-r9			INTEGER (0..maxSessionPerPMCH-1),
	...
}

PMCH-Config-r9 ::=					SEQUENCE {
	sf-AllocEnd-r9						INTEGER (0..1535),
	dataMCS-r9							INTEGER (0..28),
	mch-SchedulingPeriod-r9			ENUMERATED {
										rf8, rf16, rf32, rf64, rf128, rf256, rf512, rf1024},
	...
}

PMCH-Config-r12 ::=					SEQUENCE {
	sf-AllocEnd-r12						INTEGER (0..1535),
	dataMCS-r12							CHOICE {
		normal-r12							INTEGER (0..28),
		higerOrder-r12						INTEGER (0..27)
	},
	mch-SchedulingPeriod-r12		ENUMERATED {
										rf4, rf8, rf16, rf32, rf64, rf128, rf256, rf512, rf1024},
	...
}

TMGI-r9 ::=						SEQUENCE {
	plmn-Id-r9							CHOICE {
		plmn-Index-r9						INTEGER (1..maxPLMN-r11),
		explicitValue-r9					PLMN-Identity
	},
	serviceId-r9						OCTET STRING (SIZE (3))
}


-- ASN1STOP

SC-MTCH-InfoList-r13 ::=			SEQUENCE (SIZE (0..maxSC-MTCH-r13)) OF SC-MTCH-Info-r13

SC-MTCH-Info-r13 ::= 				SEQUENCE	{
	mbmsSessionInfo-r13						MBMSSessionInfo-r13,
	g-RNTI-r13								C-RNTI,
	sc-mtch-schedulingInfo-r13				SC-MTCH-SchedulingInfo-r13			OPTIONAL,
	sc-mtch-neighbourCell-r13				BIT STRING (SIZE(maxNeighCellSCPTM-r13))	OPTIONAL,
	...
}

MBMSSessionInfo-r13 ::=				SEQUENCE	{
	tmgi-r13								TMGI-r9,
	sessionId-r13							OCTET STRING (SIZE (1))		OPTIONAL 	-- Need OR
}

SC-MTCH-SchedulingInfo-r13::=		SEQUENCE	{
	onDurationTimerSCPTM-r13				ENUMERATED {
												psf1, psf2, psf3, psf4, psf5, psf6,
												psf8, psf10, psf20, psf30, psf40,
												psf50, psf60, psf80, psf100,
												psf200},
	drx-InactivityTimerSCPTM-r13			ENUMERATED {
												psf0, psf1, psf2, psf4, psf8,
												psf10, psf20, psf40,
												psf80, psf160, ps320,
												psf640, psf960,
												psf1280, psf1920, psf2560},
	schedulingPeriodStartOffsetSCPTM-r13	CHOICE {
		sf10									INTEGER(0..9),
		sf20									INTEGER(0..19),
		sf32									INTEGER(0..31),
		sf40									INTEGER(0..39),
		sf64									INTEGER(0..63),
		sf80									INTEGER(0..79),
		sf128									INTEGER(0..127),
		sf160									INTEGER(0..159),
		sf256									INTEGER(0..255),
		sf320									INTEGER(0..319),
		sf512									INTEGER(0..511),
		sf640									INTEGER(0..639),
		sf1024									INTEGER(0..1023)
	},
	...
}

-- ASN1STOP

SCPTMNeighbourCellList-r13 ::=		SEQUENCE (SIZE (1..maxNeighCellSCPTM-r13)) OF CellIdentity

-- ASN1STOP

SL-CommConfig-r12 ::= 				SEQUENCE	{
	commTxResources-r12					CHOICE {
		release								NULL,
		setup								CHOICE {
			scheduled-r12					SEQUENCE {
				sl-RNTI-r12						C-RNTI,
				mac-MainConfig-r12				MAC-MainConfigSL-r12,
				sc-CommTxConfig-r12				SL-CommResourcePool-r12,
				mcs-r12							INTEGER (0..28) 				OPTIONAL	-- Need OP
			},
			ue-Selected-r12					SEQUENCE {
				-- Pool for normal usage
				commTxPoolNormalDedicated-r12	SEQUENCE {
					poolToReleaseList-r12			SL-TxPoolToReleaseList-r12 OPTIONAL,	-- Need ON
					poolToAddModList-r12			SL-CommTxPoolToAddModList-r12 OPTIONAL	-- Need ON
				}
			}
		}
	}																		OPTIONAL,	-- Need ON
--	...,
	[[	scheduled-r13x0						CHOICE {
			release								NULL,
			setup								SEQUENCE {
				logicalChGroupInfoList-r13			LogicalChGroupInfoList-r13,
				multipleTxAllowed-r13				BOOLEAN
			}
		}																	OPTIONAL,	-- Need ON
		ue-Selected-r13x0					SEQUENCE {
			commTxPoolNormalDedicatedExt-r13	SEQUENCE {
				poolToReleaseListExt-r13			SL-TxPoolToReleaseListExt-r13 OPTIONAL,	-- Need ON
				poolToAddModListExt-r13				SL-CommTxPoolToAddModListExt-r13	OPTIONAL	-- Need ON
			}
		}																OPTIONAL,	-- Need ON
		commTxAllowRelayDedicated-r13		BOOLEAN			OPTIONAL	-- Need ON
	]]}

LogicalChGroupInfoList-r13 ::=		SEQUENCE (SIZE (1..maxLCG-r13)) OF SL-PriorityList-r13

SL-CommTxPoolToAddModList-r12 ::=		SEQUENCE (SIZE (1..maxSL-TxPool-r12)) OF SL-CommTxPoolToAddMod-r12

SL-CommTxPoolToAddModListExt-r13 ::=	SEQUENCE (SIZE (1..maxSL-CommTxPool-v13x0)) OF SL-CommTxPoolToAddModExt-r13

SL-CommTxPoolToAddMod-r12 ::=		SEQUENCE	{
	poolIdentity-r12					SL-TxPoolIdentity-r12,
	pool-r12							SL-CommResourcePool-r12
}

SL-CommTxPoolToAddModExt-r13 ::=		SEQUENCE	{
	poolIdentity-v13x0					SL-CommTxPoolIdentity-v13x0,
	pool-r13							SL-CommResourcePool-r12
}

MAC-MainConfigSL-r12 ::= 		SEQUENCE	{
	periodic-BSR-TimerSL					PeriodicBSR-Timer-r12 		OPTIONAL, 	-- Need ON
	retx-BSR-TimerSL						RetxBSR-Timer-r12
}

-- ASN1STOP

SL-CommTxPoolList-r12 ::=		SEQUENCE (SIZE (1..maxSL-TxPool-r12)) OF SL-CommResourcePool-r12

SL-CommTxPoolListExt-r13 ::=	SEQUENCE (SIZE (1..maxSL-CommTxPool-v13x0)) OF SL-CommResourcePool-r12

SL-CommRxPoolList-r12 ::=		SEQUENCE (SIZE (1..maxSL-RxPool-r12)) OF SL-CommResourcePool-r12

SL-CommResourcePool-r12 ::=		SEQUENCE {
	sc-CP-Len-r12						SL-CP-Len-r12,
	sc-Period-r12						SL-PeriodComm-r12,
	sc-TF-ResourceConfig-r12			SL-TF-ResourceConfig-r12,
	data-CP-Len-r12						SL-CP-Len-r12,
	dataHoppingConfig-r12				SL-HoppingConfigComm-r12,
	ue-SelectedResourceConfig-r12			SEQUENCE {
		data-TF-ResourceConfig-r12				SL-TF-ResourceConfig-r12,
		trpt-Subset-r12						SL-TRPT-Subset-r12 	OPTIONAL	-- Need OP
	}																OPTIONAL, 	-- Need OR
	rxParametersNCell-r12				SEQUENCE {
		tdd-Config-r12					TDD-Config					OPTIONAL, 	-- Need OP
		syncConfigIndex-r12			INTEGER (0..15)
	} 																OPTIONAL, 	-- Need OR
	txParameters-r12					SEQUENCE {
		sc-TxParameters-r12				SL-TxParameters-r12,
		dataTxParameters-r12			SL-TxParameters-r12
	} 																OPTIONAL, 	-- Cond Tx
--	...,
	[[	priorityList-r13				SL-PriorityList-r13			OPTIONAL 	-- Cond Tx
	]]

}

SL-TRPT-Subset-r12 ::=			BIT STRING (SIZE (3..5))

-- ASN1STOP

SL-CP-Len-r12 ::=				ENUMERATED {normal, extended}

-- ASN1STOP

SL-DiscConfig-r12 ::=					SEQUENCE {
	discTxResources-r12						CHOICE {
		release								NULL,
		setup								CHOICE {
			scheduled-r12					SEQUENCE {
				discTxConfig-r12					SL-DiscResourcePool-r12	OPTIONAL, -- Need ON
				discTF-IndexList-r12				SL-TF-IndexPairList-r12 	OPTIONAL, -- Need ON
				discHoppingConfig-r12				SL-HoppingConfigDisc-r12
														OPTIONAL	-- Need ON
			},
			ue-Selected-r12					SEQUENCE {
				discTxPoolDedicated-r12			SEQUENCE {
					poolToReleaseList-r12			SL-TxPoolToReleaseList-r12 OPTIONAL,	-- Need ON
					poolToAddModList-r12			SL-DiscTxPoolToAddModList-r12 OPTIONAL	-- Need ON
				} 													OPTIONAL	-- Need ON
			}
		}
	}																OPTIONAL,	-- Need ON
--	...,
	[[	discTF-IndexList-v1260				CHOICE {
			release								NULL,
			setup								SEQUENCE {
				discTF-IndexList-r12b				SL-TF-IndexPairList-r12b
			}
		}															OPTIONAL	-- Need ON
	]],
	[[	discTxResourcesPS-r13			CHOICE {
			release								NULL,
			setup								CHOICE {
				scheduled-r13						SL-DiscTxConfigScheduled-r13,
				ue-Selected-r13						SEQUENCE {
					discTxPoolPS-Dedicated-r13			SL-DiscTxPoolDedicated-r13
				}
			}
		}															OPTIONAL,	-- Need ON
		discTxInterFreqInfo-r13			CHOICE {
			release								NULL,
			setup								SEQUENCE {
				discTxCarrierFreq-r13				ARFCN-ValueEUTRA-r9			OPTIONAL,	-- Need OR
				discTxRefCarrierDedicated-r13		SL-DiscTxRefCarrierDedicated-r13	OPTIONAL,	-- Need OR
				discTxInfoInterFreqListExt-r13			SL-DiscTxInfoInterFreqListExt-r13	OPTIONAL	-- Need ON
			}
		}															OPTIONAL,	-- Need ON
		gapRequestsAllowedDedicated-r13		ENUMERATED {false, true}	OPTIONAL,	-- Need ON
		discRxGapConfig-r13					CHOICE {
			release								NULL,
			setup								SL-GapConfig-r13
		}															OPTIONAL,	-- Need ON
		discTxGapConfig-r13					CHOICE {
			release								NULL,
			setup								SL-GapConfig-r13
		}															OPTIONAL,	-- Need ON
		discSysInfoReportConfig-r13			CHOICE {
			release								NULL,
			setup								SL-DiscSysInfoReportFreqList-r13
		}															OPTIONAL	-- Need ON
	]]
}

SL-DiscSysInfoReportFreqList-r13 ::= SEQUENCE (SIZE (1..maxFreq)) OF ARFCN-ValueEUTRA-r9

SL-DiscTxInfoInterFreqListExt-r13 ::=	SEQUENCE {
	discTxFreqToAddModList-r13				SEQUENCE (SIZE (1..maxFreq)) OF SL-DiscTxResourceInfoPerFreq-r13	OPTIONAL,	-- Need ON
	discTxFreqToReleaseList-r13				SEQUENCE (SIZE (1..maxFreq)) OF ARFCN-ValueEUTRA-r9	OPTIONAL	-- Need ON
}

SL-DiscTxResourceInfoPerFreq-r13 ::=	SEQUENCE	{
	discTxCarrierFreq-r13					ARFCN-ValueEUTRA-r9,
	discTxResources-r13						SL-DiscTxResource-r13	OPTIONAL,	-- Need OR
	discTxResourcesPS-r13					SL-DiscTxResource-r13	OPTIONAL,	-- Need OR
	discTxRefCarrierDedicated-r13			SL-DiscTxRefCarrierDedicated-r13	OPTIONAL,	-- Need OR
	cellSelectionInfo-r13					CellSelectionInfoNFreq-r13			OPTIONAL	-- Need OR
}

SL-DiscTxResource-r13 ::=				CHOICE {
	release								NULL,
	setup								CHOICE {
		scheduled-r13					SEQUENCE {
			discTxConfig-r13					SL-DiscResourcePool-r12	OPTIONAL, -- Need ON
			discTF-IndexList-r13				SL-TF-IndexPairList-r12b	OPTIONAL, -- Need ON
			discHoppingConfig-r13				SL-HoppingConfigDisc-r12
													OPTIONAL	-- Need ON
		},
		ue-Selected-r13					SEQUENCE {
			discTxPoolDedicated-r13			SEQUENCE {
				poolToReleaseList-r13			SL-TxPoolToReleaseList-r12 OPTIONAL,	-- Need ON
				poolToAddModList-r13			SL-DiscTxPoolToAddModList-r12 OPTIONAL	-- Need ON
			} 													OPTIONAL	-- Need ON
		}
	}
}

SL-DiscTxPoolToAddModList-r12 ::=		SEQUENCE (SIZE (1..maxSL-TxPool-r12)) OF SL-DiscTxPoolToAddMod-r12

SL-DiscTxPoolToAddMod-r12 ::=		SEQUENCE	{
	poolIdentity-r12					SL-TxPoolIdentity-r12,
	pool-r12							SL-DiscResourcePool-r12
}

SL-DiscTxConfigScheduled-r13 ::=			SEQUENCE {
	discTxConfig-r12					SL-DiscResourcePool-r12	OPTIONAL, -- Need ON
	discTF-IndexList-r12				SL-TF-IndexPairList-r12 	OPTIONAL, -- Need ON
	discHoppingConfig-r12				SL-HoppingConfigDisc-r12
}

SL-DiscTxPoolDedicated-r13 ::=			SEQUENCE {
	poolToReleaseList-r12			SL-TxPoolToReleaseList-r12 OPTIONAL,	-- Need ON
	poolToAddModList-r12			SL-DiscTxPoolToAddModList-r12 OPTIONAL	-- Need ON
}

SL-TF-IndexPairList-r12 ::=		SEQUENCE (SIZE (1..maxSL-TF-IndexPair-r12)) OF SL-TF-IndexPair-r12

SL-TF-IndexPair-r12 ::=		SEQUENCE	{
	discSF-Index-r12					INTEGER (1.. 200)		OPTIONAL,	-- Need ON
	discPRB-Index-r12					INTEGER (1.. 50)		OPTIONAL	-- Need ON
}

SL-TF-IndexPairList-r12b ::=		SEQUENCE (SIZE (1..maxSL-TF-IndexPair-r12)) OF SL-TF-IndexPair-r12b

SL-TF-IndexPair-r12b ::=		SEQUENCE	{
	discSF-Index-r12b					INTEGER (0..209)		OPTIONAL,	 -- Need ON
	discPRB-Index-r12b					INTEGER (0..49)			OPTIONAL	 -- Need ON
}

SL-DiscTxRefCarrierDedicated-r13 ::=	CHOICE {
	pCell								NULL,
	sCell								SCellIndex-r10
}

-- ASN1STOP

SL-DiscTxPoolList-r12 ::=		SEQUENCE (SIZE (1..maxSL-TxPool-r12)) OF SL-DiscResourcePool-r12

SL-DiscRxPoolList-r12 ::=		SEQUENCE (SIZE (1..maxSL-RxPool-r12)) OF SL-DiscResourcePool-r12

SL-DiscResourcePool-r12 ::=		SEQUENCE	{
	cp-Len-r12						SL-CP-Len-r12,
	discPeriod-r12				ENUMERATED {rf32, rf64, rf128,
											rf256, rf512, rf1024, rf16-v13x0, spare},
	numRetx-r12					INTEGER (0..3),
	numRepetition-r12				INTEGER (1..50),
	tf-ResourceConfig-r12			SL-TF-ResourceConfig-r12,
	txParameters-r12				SEQUENCE {
		txParametersGeneral-r12		SL-TxParameters-r12,
		ue-SelectedResourceConfig-r12	SEQUENCE {
			poolSelection-r12				CHOICE {
				rsrpBased-r12					SL-PoolSelectionConfig-r12,
				random-r12						NULL
			},
			txProbability-r12			ENUMERATED {p25, p50, p75, p100}
		}															OPTIONAL 	-- Need OR
	}																OPTIONAL, 	-- Cond Tx
	rxParameters-r12				SEQUENCE {
		tdd-Config-r12					TDD-Config					OPTIONAL, 	-- Need OR
		syncConfigIndex-r12			INTEGER (0..15)
	}																OPTIONAL, 	-- Need OR
--	...,
	[[	discPeriod-v13x0				CHOICE {
			release								NULL,
			setup								ENUMERATED {rf4, rf7, rf8, rf14, rf28,
													spare3, spare2, spare}
			}														OPTIONAL,	-- Need ON
	-- Note: Extended values apply for PS discovery (not only for relay). E-UTRAN sets original
	-- field to spare value to ensure legacy UEs ignore the concerned entry
		rxParamsAddNeighFreq-r13		SEQUENCE {
			physCellId-r13					PhysCellId
		}															OPTIONAL,	-- Need ON
		txParamsAddNeighFreq-r13		SEQUENCE {
			physCellId-r13					PhysCellId,
			p-Max							P-Max					OPTIONAL,	-- Need OP
			tdd-Config-r13					TDD-Config				OPTIONAL,	-- Need OR
			tdd-Config-v1130				TDD-Config-v1130		OPTIONAL,	-- Cond TDD-OR
			freqInfo							SEQUENCE {
				ul-CarrierFreq						ARFCN-ValueEUTRA	OPTIONAL,	-- Need OP
				ul-Bandwidth						ENUMERATED {n6, n15, n25, n50, n75, n100}
																			OPTIONAL,	-- Need OP
			additionalSpectrumEmission			AdditionalSpectrumEmission
			},
			referenceSignalPower				INTEGER (-60..50),
			syncConfigIndex-r13				INTEGER (0..15)			OPTIONAL	-- Need OR
		}															OPTIONAL	-- Need ON
	]]
}

SL-PoolSelectionConfig-r12 ::=		SEQUENCE {
	threshLow-r12							RSRP-RangeSL2-r12,
	threshHigh-r12							RSRP-RangeSL2-r12
}

-- ASN1STOP

SL-DiscTxPowerInfoList-r12 ::= 	SEQUENCE (SIZE (maxSL-DiscPowerClass-r12)) OF SL-DiscTxPowerInfo-r12

SL-DiscTxPowerInfo-r12 ::= 				SEQUENCE	{
	discMaxTxPower-r12							P-Max,
	...
}

-- ASN1STOP

SL-GapConfig-r13 ::=				SEQUENCE {
	gapPatternList-r13				SL-GapPatternList-r13
}

SL-GapPatternList-r13 ::=	SEQUENCE (SIZE (1..maxSL-GP-r13)) OF SL-GapPattern-r13

SL-GapPattern-r13 ::=				SEQUENCE {
	gapPeriod-r13						ENUMERATED {rf4, rf7, rf8, rf14, rf16, rf28, rf32,
											 rf64, rf128, rf256, rf512, rf1024, spare},
	gapOffset-r12						SL-OffsetIndicator-r12,
	gapSubframeBitmap-r13 				BIT STRING (SIZE (1..10240))
}

-- ASN1STOP

SL-GapRequest-r13 ::=				SEQUENCE (SIZE (1..maxFreq)) OF SL-GapFreqInfo-r13

SL-GapFreqInfo-r13 ::=				SEQUENCE {
	carrierFreq-r13					ARFCN-ValueEUTRA-r9					OPTIONAL,
	gapPatternList-r13				SL-GapPatternList-r13
}

-- ASN1STOP

SL-HoppingConfigComm-r12 ::=		SEQUENCE	{
	hoppingParameter-r12				INTEGER (0..504),
	numSubbands-r12						ENUMERATED {ns1, ns2, ns4},
	rb-Offset-r12						INTEGER (0..110)
}

SL-HoppingConfigDisc-r12 ::=	SEQUENCE	{
	a-r12									INTEGER (1..200),
	b-r12									INTEGER (1..10),
	c-r12									ENUMERATED {n1, n5}
}

-- ASN1STOP

SL-OffsetIndicator-r12 ::=			CHOICE {
	small-r12								INTEGER (0..319),
	large-r12								INTEGER (0..10239)
}

SL-OffsetIndicatorSync-r12 ::=			INTEGER (0..39)

-- ASN1STOP

SL-PeriodComm-r12 ::=					ENUMERATED {sf40, sf60, sf70, sf80, sf120, sf140,
												 sf160, sf240, sf280, sf320, spare6, spare5,
												 spare4, spare3, spare2, spare}

-- ASN1STOP

SL-PriorityList-r13 ::=		SEQUENCE (SIZE (1..maxSL-Prio-r13)) OF SL-Priority-r13

SL-Priority-r13 ::=			INTEGER (1..8)

-- ASN1STOP

SLSSID-r12 ::=					INTEGER (0..167)

-- ASN1STOP

SL-SyncConfigList-r12 ::=		SEQUENCE (SIZE (1..maxSL-SyncConfig-r12)) OF SL-SyncConfig-r12

SL-SyncConfig-r12 ::=					SEQUENCE {
	syncCP-Len-r12							SL-CP-Len-r12,
	syncOffsetIndicator-r12				SL-OffsetIndicatorSync-r12,
	slssid-r12								SLSSID-r12,
	txParameters-r12							SEQUENCE {
		syncTxParameters-r12					SL-TxParameters-r12,
		syncTxThreshIC-r12						RSRP-RangeSL-r12,
		syncInfoReserved-r12						BIT STRING (SIZE (19))	OPTIONAL 	-- Need OR
	}																	OPTIONAL, 	-- Need OR
	rxParamsNCell-r12						SEQUENCE {
		physCellId-r12							PhysCellId,
		discSyncWindow-r12				ENUMERATED {w1, w2}
	}																	OPTIONAL, 	-- Need OR
--	...,
	[[	syncTxPeriodic-r13					ENUMERATED {true}			OPTIONAL	-- Need OR
	]]
}

SL-SyncConfigListNFreq-r12 ::=		SEQUENCE (SIZE (1..maxSL-SyncConfig-r12)) OF SL-SyncConfigNFreq-r13

SL-SyncConfigNFreq-r13 ::=			SEQUENCE {
	asyncParameters-r13					SEQUENCE {
		syncCP-Len-r13						SL-CP-Len-r12,
		syncOffsetIndicator-r13				SL-OffsetIndicatorSync-r12,
		slssid-r13							SLSSID-r12
	}																OPTIONAL,	-- Need OR
	txParameters-r13					SEQUENCE {
		syncTxParameters-r13				SL-TxParameters-r12,
		syncTxThreshIC-r13					RSRP-RangeSL-r12,
		syncInfoReserved-r13					BIT STRING (SIZE (19))	OPTIONAL,	-- Need OR
		syncTxPeriodic-r13					ENUMERATED {true}		OPTIONAL	-- Need OR
	}																OPTIONAL,	-- Need OR
	rxParameters-r1s					SEQUENCE {
		discSyncWindow-r13					ENUMERATED {w1, w2}
	}																	OPTIONAL, 	-- Need OR
	...
}
-- ASN1STOP

SL-SysInfoReport-r13 ::=			SEQUENCE {
	plmn-IdentityList-r13				PLMN-IdentityList			OPTIONAL,
	cellIdentity-13						CellIdentity				OPTIONAL,
	carrierFreqInfo-13					ARFCN-ValueEUTRA-r9			OPTIONAL,
	discRxResources-r13					SL-DiscRxPoolList-r12		OPTIONAL,
	discTxPoolCommon-r13				SL-DiscTxPoolList-r12 		OPTIONAL,
	discTxPowerInfo-r13					SL-DiscTxPowerInfoList-r12	OPTIONAL,
	discSyncConfig-r13				SEQUENCE {
		asyncParameters-r13					SEQUENCE {
			syncCP-Len-r13						SL-CP-Len-r12,
			syncOffsetIndicator-r13				SL-OffsetIndicatorSync-r12,
			slssid-r13							SLSSID-r12
		}															OPTIONAL,
		txParameters-r13					SEQUENCE {
			syncTxParameters-r13				SL-TxParameters-r12,
			syncTxThreshIC-r13					RSRP-RangeSL-r12,
			syncInfoReserved-r13				BIT STRING (SIZE (19))	OPTIONAL,
			syncTxPeriodic-r13					ENUMERATED {true}		OPTIONAL
		}																OPTIONAL
	}																OPTIONAL,
	cellSelectionInfo-r13			SEQUENCE {
		q-RxLevMin-r13					Q-RxLevMin,
		q-RxLevMinOffset-r13			INTEGER (1..8)				OPTIONAL
	}	OPTIONAL,
	q-Hyst-r13						ENUMERATED {
												dB0, dB1, dB2, dB3, dB4, dB5, dB6, dB8, dB10,
												dB12, dB14, dB16, dB18, dB20, dB22, dB24}
																	OPTIONAL,
	q-RxLevMin-r13					Q-RxLevMin	OPTIONAL,
	t-ReselectionEUTRA-r13			T-Reselection	OPTIONAL,
	tdd-Config-r13					TDD-Config		OPTIONAL,
	freqInfo-r13					SEQUENCE {
		ul-CarrierFreq-r13				ARFCN-ValueEUTRA				OPTIONAL,	
		ul-Bandwidth-r13				ENUMERATED {n6, n15, n25, n50, n75, n100}
																		OPTIONAL,	
		additionalSpectrumEmission-r13	AdditionalSpectrumEmission		OPTIONAL
	}																OPTIONAL,
	p-Max-r13						P-Max	OPTIONAL,
	referenceSignalPower-r13		INTEGER (-60..50)	OPTIONAL
}

-- ASN1STOP

SL-TF-ResourceConfig-r12 ::=		SEQUENCE	{
	prb-Num-r12							INTEGER (1..100),
	prb-Start-r12 				 		INTEGER (0..99),
	prb-End-r12				 			INTEGER (0..99),
	offsetIndicator-r12					SL-OffsetIndicator-r12,
	subframeBitmap-r12 					SubframeBitmapSL-r12
}

SubframeBitmapSL-r12 ::=		CHOICE {
	bs4-r12									BIT STRING (SIZE (4)),
	bs8-r12									BIT STRING (SIZE (8)),
	bs12-r12								BIT STRING (SIZE (12)),
	bs16-r12								BIT STRING (SIZE (16)),
	bs30-r12								BIT STRING (SIZE (30)),
	bs40-r12								BIT STRING (SIZE (40)),
	bs42-r12								BIT STRING (SIZE (42))
}

-- ASN1STOP

SL-TxParameters-r12 ::=				SEQUENCE	{
	alpha-r12								Alpha-r12,
	p0-r12									P0-SL-r12
}

P0-SL-r12 ::=							INTEGER (-126..31)

-- ASN1STOP

SL-TxPoolIdentity-r12 ::=			INTEGER (1.. maxSL-TxPool-r12)

SL-CommTxPoolIdentity-v13x0 ::=		INTEGER (maxSL-CommTxPool-r12Plus1-r13.. maxSL-CommTxPool-r13)

SL-CommTxPoolIdentity-r13 ::=		INTEGER (1.. maxSL-CommTxPool-r13)

-- ASN1STOP

SL-TxPoolToReleaseList-r12 ::=	SEQUENCE (SIZE (1..maxSL-TxPool-r12)) OF SL-TxPoolIdentity-r12

SL-TxPoolToReleaseListExt-r13 ::=	SEQUENCE (SIZE (1..maxSL-CommTxPool-v13x0)) OF SL-CommTxPoolIdentity-v13x0

-- ASN1STOP
maxACDC-Cat-r13				INTEGER ::=	16	-- Maximum number of ACDC categories (per PLMN)
maxBandComb-r10				INTEGER ::=	128	-- Maximum number of band combinations.
maxBandComb-r11				INTEGER ::=	256	-- Maximum number of additional band combinations.
maxBandComb-r13				INTEGER ::=	384 -- Maximum number of band combinations in Rel-13
maxBands					INTEGER ::= 64	-- Maximum number of bands listed in EUTRA UE caps
maxBandwidthClass-r10		INTEGER ::=	16	-- Maximum number of supported CA BW classes per band
maxBandwidthCombSet-r10		INTEGER ::=	32	-- Maximum number of bandwidth combination sets per
											-- supported band combination
maxCDMA-BandClass			INTEGER ::= 32	-- Maximum value of the CDMA band classes
maxCellBlack				INTEGER ::= 16	-- Maximum number of blacklisted physical cell identity
											-- ranges listed in SIB type 4 and 5
maxCellHistory-r12			INTEGER ::= 16	-- Maximum number of visited EUTRA cells reported
maxCellInfoGERAN-r9 		INTEGER ::=	32	-- Maximum number of GERAN cells for which system in-
											-- formation can be provided as redirection assistance
maxCellInfoUTRA-r9			INTEGER ::=	16	-- Maximum number of UTRA cells for which system
											-- information can be provided as redirection
											-- assistance
maxCombIDC-r11				INTEGER ::= 128	-- Maximum number of reported UL CA combinations
maxCSI-IM-r11				INTEGER ::= 3	-- Maximum number of CSI-IM configurations
											-- (per carrier frequency)
maxCSI-IM-r12				INTEGER ::= 4	-- Maximum number of CSI-IM configurations
											-- (per carrier frequency)
maxCSI-Proc-r11				INTEGER ::= 4	-- Maximum number of CSI processes (per carrier
											--  frequency)
maxCSI-RS-NZP-r11			INTEGER ::= 3	-- Maximum number of CSI RS resource
											--  configurations using non-zero Tx power
											--  (per carrier frequency)
maxCSI-RS-ZP-r11			INTEGER ::= 4	-- Maximum number of CSI RS resource
											--  configurations using zero Tx power(per carrier
											--  frequency)
maxCQI-ProcExt-r11			INTEGER ::= 3	-- Maximum number of additional periodic CQI
											-- configurations (per carrier frequency)
maxFreqUTRA-TDD-r10			INTEGER ::=	6	-- Maximum number of UTRA TDD carrier frequencies for
											-- which system information can be provided as
											-- redirection assistance
maxCellInter				INTEGER ::= 16	-- Maximum number of neighbouring inter-frequency
											-- cells listed in SIB type 5
maxCellIntra				INTEGER ::= 16	-- Maximum number of neighbouring intra-frequency
											-- cells listed in SIB type 4
maxCellListGERAN			INTEGER ::= 3	-- Maximum number of lists of GERAN cells
maxCellMeas					INTEGER ::= 32	-- Maximum number of entries in each of the
											-- cell lists in a measurement object
maxCellReport				INTEGER ::= 8	-- Maximum number of reported cells/CSI-RS resources
maxCSI-RS-Meas-r12			INTEGER ::= 96	-- Maximum number of entries in the CSI-RS list
											-- in a measurement object
maxDRB						INTEGER ::= 11	-- Maximum number of Data Radio Bearers
maxDS-Duration-r12			INTEGER ::= 5	-- Maximum number of subframes in a discovery signals
											-- occasion
maxDS-ZTP-CSI-RS-r12		INTEGER ::= 5	-- Maximum number of zero transmission power CSI-RS for
											-- a serving cell concerning discovery signals
maxEARFCN					INTEGER ::= 65535	-- Maximum value of EUTRA carrier frequency
maxEARFCN-Plus1				INTEGER ::= 65536	-- Lowest value extended EARFCN range
maxEARFCN2					INTEGER ::= 262143	-- Highest value extended EARFCN range
maxEPDCCH-Set-r11			INTEGER ::= 2	-- Maximum number of EPDCCH sets
maxFBI						INTEGER ::= 64	-- Maximum value of fequency band indicator
maxFBI-Plus1					INTEGER ::= 65	-- Lowest value extended FBI range
maxFBI2						INTEGER ::= 256	-- Highest value extended FBI range
maxFreq						INTEGER ::= 8	-- Maximum number of carrier frequencies
maxFreqIDC-r11				INTEGER ::= 32	-- Maximum number of carrier frequencies that are
											-- affected by the IDC problems
maxFreqMBMS-r11				INTEGER ::= 5	-- Maximum number of carrier frequencies for which an 
											-- MBMS capable UE may indicate an interest
maxGERAN-SI					INTEGER ::= 10	-- Maximum number of GERAN SI blocks that can be
											-- provided as part of NACC information
maxGNFG						INTEGER ::= 16	-- Maximum number of GERAN neighbour freq groups
maxLCG-r13					INTEGER ::= 4	-- Maximum number of logical channel groups
maxLogMeasReport-r10		INTEGER ::= 520	-- Maximum number of logged measurement entries
											--  that can be reported by the UE in one message
maxMBSFN-Allocations		INTEGER ::= 8	-- Maximum number of MBSFN frame allocations with
											-- different offset
maxMBSFN-Area				INTEGER ::= 8
maxMBSFN-Area-1				INTEGER ::= 7
maxMBMSServiceListPerUE-r13		INTEGER ::= 16	-- Maximum number of services which the UE can
										-- include in the MBMS interest indication
maxMeasId					INTEGER ::= 32
maxMeasId-Plus1 			INTEGER ::= 33
maxMeasId-r12				INTEGER ::= 64
maxMultiBands				INTEGER ::= 8	-- Maximum number of additional frequency bands
											-- that a cell belongs to
maxNS-Pmax-r10				INTEGER ::= 8	-- Maximum number of NS and P-Max values per band
maxNAICS-Entries-r12			INTEGER ::= 8	-- Maximum number of supported NAICS combination(s)
maxNeighCell-r12				INTEGER ::= 8	-- Maximum number of neighbouring cells in NAICS
											-- configuration (per carrier frequency)
maxNeighCellSCPTM-r13		INTEGER ::=	8	-- Maximum number of SCPTM neighbour cells
maxObjectId					INTEGER ::= 32
maxP-a-PerNeighCell-r12		INTEGER ::= 3	-- Maximum number of power offsets for a neighbour cell
											-- in NAICS configuration
maxPageRec					INTEGER ::= 16	-- 
maxPhysCellIdRange-r9 		INTEGER ::= 4	-- Maximum number of physical cell identity ranges
maxPLMN-r11					INTEGER ::=	6	-- Maximum number of PLMNs
maxPNOffset					INTEGER ::=	511	-- Maximum number of CDMA2000 PNOffsets
maxPMCH-PerMBSFN			INTEGER ::= 15
maxQCI-r13					INTEGER ::= 6   -- Maximum number of QCIs
maxRAT-Capabilities			INTEGER ::= 8	-- Maximum number of interworking RATs (incl EUTRA)
maxRE-MapQCL-r11			INTEGER ::= 4	-- Maximum number of PDSCH RE Mapping configurations
											--  (per carrier frequency)
maxReportConfigId			INTEGER ::= 32
maxRSTD-Freq-r10			INTEGER ::= 3	-- Maximum number of frequency layers for RSTD
											-- measurement
maxSAI-MBMS-r11				INTEGER ::= 64	-- Maximum number of MBMS service area identities
											-- broadcast per carrier frequency
maxSCell-r10				INTEGER ::= 4	-- Maximum number of SCells
maxSCell-r13				INTEGER ::= 31	-- Highest value of extended number range of SCells
maxSCell-Plus1				INTEGER ::= 5	-- Lowest value of extended number range of SCells
maxSC-MTCH-r13				INTEGER ::= 1024	-- Maximum number of SC-MTCHs in one cell
maxSL-CommRxPoolNFreq-r13	INTEGER ::= 32	-- Maximum number of individual sidelink communication
											-- Rx resource pools on neighbouring freq
maxSL-CommRxPoolPreconf-v13x0	INTEGER ::= 12	-- Maximum number of additional preconfigured
												-- sidelink communication Rx resource pool entries
maxSL-CommTxPool-r12Plus1-r13	INTEGER ::= 5	-- First additional individual sidelink
											-- communication Tx resource pool
maxSL-CommTxPool-v13x0			INTEGER ::= 4	-- Maximum number of additional sidelink
												-- communication Tx resource pool entries
maxSL-CommTxPool-r13			INTEGER ::= 8	-- Maximum number of individual sidelink
												-- communication Tx resource pools
maxSL-CommTxPoolPreconf-v13x0	INTEGER ::= 7	-- Maximum number of additional preconfigured
												-- sidelink communication Tx resource pool entries
maxSL-Dest-r12			INTEGER ::= 16	-- Maximum number of sidelink destinations
maxSL-DiscPowerClass-r12	INTEGER ::= 3	-- Maximum number of sidelink power classes
maxSL-DiscRxPoolPreconf-r13		INTEGER ::= 4	-- Maximum number of preconfigured sidelink
												-- discovery Rx resource pool entries
maxSL-DiscSysInfoReportFreq-r13	INTEGER ::= 8	-- Maximum number of frequencies to include in a
												-- UESidelinkInformation for SI reporting
maxSL-DiscTxPoolPreconf-r13		INTEGER ::= 1	-- Maximum number of preconfigured sidelink
												-- discovery Tx resource pool entries
maxSL-GP-r13			INTEGER ::= 8	-- Maximum number of gap patterns that can be requested
										-- for a frequency or assigned
maxSL-Prio-r13			INTEGER ::= 8	-- Maximum number of entries in sidelink priority list
maxSL-RxPool-r12			INTEGER ::= 16	-- Maximum number of individual sidelink Rx resource pools
maxSL-SyncConfig-r12		INTEGER ::= 16	-- Maximum number of sidelink Sync configurations
maxSL-TF-IndexPair-r12	INTEGER ::= 64	-- Maximum number of sidelink Time Freq resource index
											--  pairs
maxSL-TxPool-r12			INTEGER ::= 4	-- Maximum number of individual sidelink Tx resource pools
maxSTAG-r11					INTEGER ::= 3	-- Maximum number of STAGs
maxServCell-r10				INTEGER ::= 5	-- Maximum number of Serving cells
maxServCell-r13				INTEGER ::= 32	-- Highest value of extended number range of Serving cells
maxServCell-Plus1			INTEGER ::= 6	-- Lowest value of extended number range of Serving cells
maxServiceCount 			INTEGER ::= 16	-- Maximum number of MBMS services that can be included
											--  in an MBMS counting request and response
maxServiceCount-1			INTEGER ::= 15
maxSessionPerPMCH			INTEGER ::= 29
maxSessionPerPMCH-1			INTEGER ::= 28
maxSIB						INTEGER ::= 32	-- Maximum number of SIBs
maxSIB-1					INTEGER ::= 31
maxSI-Message				INTEGER ::= 32	-- Maximum number of SI messages
maxSimultaneousBands-r10	INTEGER ::= 64	-- Maximum number of simultaneously aggregated bands
maxSubframePatternIDC-r11	INTEGER ::= 8	-- Maximum number of subframe reservation patterns
											-- that the UE can simultaneously recommend to the
											-- E-UTRAN for use.
maxUTRA-FDD-Carrier			INTEGER ::= 16	-- Maximum number of UTRA FDD carrier frequencies
maxUTRA-TDD-Carrier			INTEGER ::= 16	-- Maximum number of UTRA TDD carrier frequencies
maxWLAN-Id-r12				INTEGER ::=	16	-- Maximum number of WLAN identifiers

-- ASN1STOP

END

-- ASN1STOP

PC5-RRC-Definitions DEFINITIONS AUTOMATIC TAGS ::=

BEGIN

IMPORTS
	TDD-ConfigSL-r12
FROM EUTRA-RRC-Definitions;

-- ASN1STOP

SBCCH-SL-BCH-Message ::= SEQUENCE {
	message					SBCCH-SL-BCH-MessageType
}

SBCCH-SL-BCH-MessageType ::=						MasterInformationBlock-SL

-- ASN1STOP

MasterInformationBlock-SL ::=		SEQUENCE {
	sl-Bandwidth-r12					ENUMERATED {
											n6, n15, n25, n50, n75, n100},
	tdd-ConfigSL-r12					TDD-ConfigSL-r12,
	directFrameNumber-r12				BIT STRING (SIZE (10)),
	directSubframeNumber-r12			INTEGER (0..9),
	inCoverage-r12						BOOLEAN,
	reserved-r12						BIT STRING (SIZE (19))
}


-- ASN1STOP

END

-- ASN1STOP

EUTRA-UE-Variables DEFINITIONS AUTOMATIC TAGS ::=

BEGIN

IMPORTS
	AbsoluteTimeInfo-r10,
	AreaConfiguration-r10,
	AreaConfiguration-v1130,
	CarrierFreqGERAN,
	CellIdentity,
	ConnEstFailReport-r11,
	SpeedStateScaleFactors,
	C-RNTI,
	LoggingDuration-r10,
	LoggingInterval-r10,
	LogMeasInfo-r10,
	MeasCSI-RS-Id-r12,
	MeasId,
	MeasId-v1250,
	MeasIdToAddModList,
	MeasIdToAddModListExt-r12,
	MeasObjectToAddModList,
	MeasObjectToAddModList-v9e0,
	MeasScaleFactor-r12,
	MobilityStateParameters,
	NeighCellConfig,
	PhysCellId,
	PhysCellIdCDMA2000,
	PhysCellIdGERAN,
	PhysCellIdUTRA-FDD,
	PhysCellIdUTRA-TDD,
	PLMN-Identity,
	PLMN-IdentityList3-r11,
	QuantityConfig,
	ReportConfigToAddModList,
	RLF-Report-r9,
	TargetMBSFN-AreaList-r12,
	TraceReference-r10,
	VisitedCellInfoList-r12,
	maxCellMeas,
	maxCSI-RS-Meas-r12,
	maxMeasId,
	maxMeasId-r12,
	UL-DelayConfig-r13
FROM EUTRA-RRC-Definitions;

-- ASN1STOP

VarConnEstFailReport-r11 ::=		SEQUENCE {
	connEstFailReport-r11				ConnEstFailReport-r11,
	plmn-Identity-r11					PLMN-Identity
}

-- ASN1STOP

VarLogMeasConfig-r10 ::=				SEQUENCE {
	areaConfiguration-r10			AreaConfiguration-r10		OPTIONAL,
	loggingDuration-r10				LoggingDuration-r10,
	loggingInterval-r10				LoggingInterval-r10
}

VarLogMeasConfig-r11 ::=		SEQUENCE {
	areaConfiguration-r10			AreaConfiguration-r10		OPTIONAL,
	areaConfiguration-v1130			AreaConfiguration-v1130		OPTIONAL,
	loggingDuration-r10				LoggingDuration-r10,
	loggingInterval-r10				LoggingInterval-r10
}

VarLogMeasConfig-r12 ::=		SEQUENCE {
	areaConfiguration-r10			AreaConfiguration-r10		OPTIONAL,
	areaConfiguration-v1130			AreaConfiguration-v1130		OPTIONAL,
	loggingDuration-r10				LoggingDuration-r10,
	loggingInterval-r10				LoggingInterval-r10,
	targetMBSFN-AreaList-r12		TargetMBSFN-AreaList-r12	OPTIONAL
}

-- ASN1STOP

VarLogMeasReport-r10 ::=				SEQUENCE {
	traceReference-r10					TraceReference-r10,
	traceRecordingSessionRef-r10			OCTET STRING (SIZE (2)),
	tce-Id-r10							OCTET STRING (SIZE (1)),
	plmn-Identity-r10					PLMN-Identity,
	absoluteTimeInfo-r10				AbsoluteTimeInfo-r10,
	logMeasInfoList-r10					LogMeasInfoList2-r10
}

VarLogMeasReport-r11 ::=			SEQUENCE {
	traceReference-r10					TraceReference-r10,
	traceRecordingSessionRef-r10		OCTET STRING (SIZE (2)),
	tce-Id-r10							OCTET STRING (SIZE (1)),
	plmn-IdentityList-r11				PLMN-IdentityList3-r11,
	absoluteTimeInfo-r10				AbsoluteTimeInfo-r10,
	logMeasInfoList-r10					LogMeasInfoList2-r10
}

LogMeasInfoList2-r10 ::=				SEQUENCE (SIZE (1..maxLogMeas-r10)) OF LogMeasInfo-r10

-- ASN1STOP

VarMeasConfig ::=					SEQUENCE {
	-- Measurement identities
	measIdList							MeasIdToAddModList					OPTIONAL,
	measIdListExt-r12					MeasIdToAddModListExt-r12			OPTIONAL,
	-- Measurement objects
	measObjectList						MeasObjectToAddModList				OPTIONAL,
	measObjectList-v9i0					MeasObjectToAddModList-v9e0			OPTIONAL,
	-- Reporting configurations
	reportConfigList					ReportConfigToAddModList			OPTIONAL,
	-- Other parameters
	quantityConfig						QuantityConfig						OPTIONAL,
	measScaleFactor-r12					MeasScaleFactor-r12					OPTIONAL, 
	s-Measure							INTEGER (-140..-44)					OPTIONAL,
	speedStatePars						CHOICE {
		release								NULL,
		setup								SEQUENCE {
			mobilityStateParameters				MobilityStateParameters,
			timeToTrigger-SF					SpeedStateScaleFactors
		}
	}																		OPTIONAL,
	allowInterruptions-r11			BOOLEAN								OPTIONAL
}

-- ASN1STOP

VarMeasReportList ::=				SEQUENCE (SIZE (1..maxMeasId)) OF VarMeasReport
VarMeasReportList-r12 ::=			SEQUENCE (SIZE (1..maxMeasId-r12)) OF VarMeasReport

VarMeasReport ::=					SEQUENCE {
	-- List of measurement that have been triggered
	measId								MeasId,
	measId-v1250						MeasId-v1250					OPTIONAL,
	cellsTriggeredList					CellsTriggeredList				OPTIONAL,
	csi-RS-TriggeredList-r12			CSI-RS-TriggeredList-r12		OPTIONAL,
	numberOfReportsSent					INTEGER
}

CellsTriggeredList ::=				SEQUENCE (SIZE (1..maxCellMeas)) OF CHOICE {
	physCellIdEUTRA							PhysCellId,
	physCellIdUTRA							CHOICE {
		fdd										PhysCellIdUTRA-FDD,
		tdd										PhysCellIdUTRA-TDD
	},
	physCellIdGERAN							SEQUENCE {
		carrierFreq								CarrierFreqGERAN,
		physCellId								PhysCellIdGERAN
	},
	physCellIdCDMA2000						PhysCellIdCDMA2000
}

CSI-RS-TriggeredList-r12 ::=		SEQUENCE (SIZE (1..maxCSI-RS-Meas-r12)) OF MeasCSI-RS-Id-r12

-- ASN1STOP
VarMobilityHistoryReport-r12 ::=	VisitedCellInfoList-r12

-- ASN1STOP

VarRLF-Report-r10 ::=				SEQUENCE {
	rlf-Report-r10							RLF-Report-r9,
	plmn-Identity-r10						PLMN-Identity
}

VarRLF-Report-r11 ::=				SEQUENCE {
	rlf-Report-r10						RLF-Report-r9,
	plmn-IdentityList-r11				PLMN-IdentityList3-r11
}

-- ASN1STOP

VarShortMAC-Input ::=					SEQUENCE {
	cellIdentity							CellIdentity,
	physCellId								PhysCellId,
	c-RNTI									C-RNTI
}
-- ASN1STOP

maxLogMeas-r10				INTEGER ::= 4060-- Maximum number of logged measurement entries
											--  that can be stored by the UE

-- ASN1STOP

END

-- ASN1STOP

EUTRA-Sidelink-Preconf DEFINITIONS AUTOMATIC TAGS ::=

BEGIN

IMPORTS
	AdditionalSpectrumEmission,
	ARFCN-ValueEUTRA-r9,
	FilterCoefficient,
	maxSL-TxPool-r12,
	maxSL-CommRxPoolPreconf-v13x0,
	maxSL-CommTxPoolPreconf-v13x0,
	maxSL-DiscRxPoolPreconf-r13,
	maxSL-DiscTxPoolPreconf-r13,
	P-Max,
	ReselectionInfoRelay-r13,
	SL-CP-Len-r12,
	SL-HoppingConfigComm-r12,
	SL-OffsetIndicatorSync-r12,
	SL-PeriodComm-r12,
	RSRP-RangeSL3-r12,
	SL-PriorityList-r13,
	SL-TF-ResourceConfig-r12,
	SL-TRPT-Subset-r12,
	P0-SL-r12,
	TDD-ConfigSL-r12
FROM EUTRA-RRC-Definitions;

-- ASN1STOP

SL-Preconfiguration-r12 ::=		SEQUENCE {
	preconfigGeneral-r12				SL-PreconfigGeneral-r12,
	preconfigSync-r12					SL-PreconfigSync-r12,
	preconfigComm-r12					SL-PreconfigCommPoolList4-r12,
--	...,
	[[	preconfigComm-v13x0				SEQUENCE {
			commRxPoolListExt-r13			SL-PreconfigCommRxPoolListExt-r13,
			commTxPoolListExt-r13			SL-PreconfigCommTxPoolListExt-r13		OPTIONAL
		}																		OPTIONAL,
		preconfigDisc-r13				SEQUENCE {
			discRxPoolList-r13				SL-PreconfigDiscRxPoolList-r13,
			discTxPoolList-r13				SL-PreconfigDiscTxPoolList-r13		OPTIONAL
		}																		OPTIONAL,
		preconfigRelay-r13				SL-PreconfigRelay-r13				OPTIONAL
	]]

}

SL-PreconfigGeneral-r12 ::=		SEQUENCE {
	-- PDCP configuration
	rohc-Profiles-r12					SEQUENCE {
		profile0x0001-r12						BOOLEAN,
		profile0x0002-r12						BOOLEAN,
		profile0x0004-r12						BOOLEAN,
		profile0x0006-r12						BOOLEAN,
		profile0x0101-r12						BOOLEAN,
		profile0x0102-r12						BOOLEAN,
		profile0x0104-r12						BOOLEAN
	},
	-- Physical configuration
	carrierFreq-r12						ARFCN-ValueEUTRA-r9,
	maxTxPower-r12						P-Max,
	additionalSpectrumEmission-r12		AdditionalSpectrumEmission,
	sl-bandwidth-r12					ENUMERATED {n6, n15, n25, n50, n75, n100},
	tdd-ConfigSL-r12					TDD-ConfigSL-r12,
	reserved-r12						BIT STRING (SIZE (19)),
	...
}

SL-PreconfigSync-r12 ::=	SEQUENCE {
	syncCP-Len-r12						SL-CP-Len-r12,
	syncOffsetIndicator1-r12			SL-OffsetIndicatorSync-r12,
	syncOffsetIndicator2-r12			SL-OffsetIndicatorSync-r12,
	syncTxParameters-r12				P0-SL-r12,
	syncTxThreshOoC-r12					RSRP-RangeSL3-r12,
	filterCoefficient-r12				FilterCoefficient,
	syncRefMinHyst-r12					ENUMERATED {dB0, dB3, dB6, dB9, dB12},
	syncRefDiffHyst-r12					ENUMERATED {dB0, dB3, dB6, dB9, dB12, dBinf},
--	...,
	[[	syncTxPeriodic-r13					ENUMERATED {true}			OPTIONAL	-- Need OR
	]]
}

SL-PreconfigCommPoolList4-r12 ::=	SEQUENCE (SIZE (1..maxSL-TxPool-r12)) OF SL-PreconfigCommPool-r12

SL-PreconfigCommRxPoolListExt-r13 ::=	SEQUENCE (SIZE (1..maxSL-CommRxPoolPreconf-v13x0)) OF SL-PreconfigCommPool-r12

SL-PreconfigCommTxPoolListExt-r13 ::=	SEQUENCE (SIZE (1..maxSL-CommTxPoolPreconf-v13x0)) OF SL-PreconfigCommPool-r12

SL-PreconfigCommPool-r12 ::=		SEQUENCE {
-- This IE is same as SL-CommResourcePool with rxParametersNCell absent
	sc-CP-Len-r12						SL-CP-Len-r12,
	sc-Period-r12						SL-PeriodComm-r12,
	sc-TF-ResourceConfig-r12			SL-TF-ResourceConfig-r12,
	sc-TxParameters-r12					P0-SL-r12,
	data-CP-Len-r12						SL-CP-Len-r12,
	data-TF-ResourceConfig-r12			SL-TF-ResourceConfig-r12,
	dataHoppingConfig-r12				SL-HoppingConfigComm-r12,
	dataTxParameters-r12				P0-SL-r12,
	trpt-Subset-r12						SL-TRPT-Subset-r12,
--	...,
	[[	priorityList-r13				SL-PriorityList-r13			OPTIONAL	-- For Tx
	]]
}

SL-PreconfigDiscRxPoolList-r13 ::=	SEQUENCE (SIZE (1..maxSL-DiscRxPoolPreconf-r13)) OF SL-PreconfigDiscPool-r13

SL-PreconfigDiscTxPoolList-r13 ::=	SEQUENCE (SIZE (1..maxSL-DiscTxPoolPreconf-r13)) OF SL-PreconfigDiscPool-r13

SL-PreconfigDiscPool-r13 ::=		SEQUENCE {
-- This IE is same as SL-DiscResourcePool with rxParameters absent
	cp-Len-r13						SL-CP-Len-r12,
	discPeriod-r13				ENUMERATED {rf4, rf7, rf8, rf14, rf16, rf28, rf32, rf64,
										 rf128, rf256, rf512, rf1024, spare4, spare3,
										 spare2, spare},
	numRetx-r13					INTEGER (0..3),
	numRepetition-r13				INTEGER (1..50),
	tf-ResourceConfig-r13			SL-TF-ResourceConfig-r12,
	txParameters-r13				SEQUENCE {
		txParametersGeneral-r13		P0-SL-r12,
		txProbability-r13			ENUMERATED {p25, p50, p75, p100}
	}																OPTIONAL,
	...
}

SL-PreconfigRelay-r13 ::=	SEQUENCE {
	reselectionInfoRemoteUE-OoC-r13			ReselectionInfoRelay-r13
}

END

-- ASN1STOP

EUTRA-InterNodeDefinitions DEFINITIONS AUTOMATIC TAGS ::=

BEGIN

IMPORTS
	AntennaInfoCommon,
	AntennaInfoDedicated-v10i0,
	ARFCN-ValueEUTRA,
	ARFCN-ValueEUTRA-v9e0,
	ARFCN-ValueEUTRA-r9,
	CellIdentity,
	C-RNTI,
	DL-DCCH-Message,
	DRB-Identity,
	DRB-ToReleaseList,
	FreqBandIndicator-r11,
	InDeviceCoexIndication-r11,
	MasterInformationBlock,
	maxBands,
	maxFreq,
	maxDRB,
	maxSCell-r10,
	maxSCell-r13,
	maxSCell-Plus1,
	maxServCell-r10,
	maxServCell-Plus1,
	maxServCell-r13,
	MBMSInterestIndication-r11,
	MeasConfig,
	MeasGapConfig,
	OtherConfig-r9,
	PhysCellId,
	P-Max,
	PowerCoordinationInfo-r12,
	SidelinkUEInformation-r12,
	SL-CommConfig-r12,
	SL-DiscConfig-r12,
	RadioResourceConfigDedicated,
	RSRP-Range,
	RSRQ-Range,
	RSRQ-Range-v1250,
	RS-SINR-Range-r13,
	SCellToAddModList-r10,
	SCellToAddModListExt-r13,
	SCG-ConfigPartSCG-r12,
	SecurityAlgorithmConfig,
	SCellIndex-r10,
	SCellIndex-r13,
	SCellToReleaseList-r10,
	SCellToReleaseListExt-r13,
	ServCellIndex-r10,
	ServCellIndexFull-r13,
	ShortMAC-I,
	MeasResultSSTD-r13,
	SystemInformationBlockType1,
	SystemInformationBlockType1-v890-IEs,
	SystemInformationBlockType2,
	UEAssistanceInformation-r11,
	UECapabilityInformation,
	UE-CapabilityRAT-ContainerList,
	UE-RadioPagingInfo-r12,
	WLAN-OffloadConfig-r12
FROM EUTRA-RRC-Definitions;

-- ASN1STOP

HandoverCommand ::=					SEQUENCE {
	criticalExtensions					CHOICE {
		c1									CHOICE{
			handoverCommand-r8					HandoverCommand-r8-IEs,
			spare7 NULL,
			spare6 NULL, spare5 NULL, spare4 NULL,
			spare3 NULL, spare2 NULL, spare1 NULL
		},
		criticalExtensionsFuture			SEQUENCE {}
	}
}

HandoverCommand-r8-IEs ::=			SEQUENCE {
	handoverCommandMessage				OCTET STRING (CONTAINING DL-DCCH-Message),
	nonCriticalExtension				SEQUENCE {}							OPTIONAL
}

-- ASN1STOP

HandoverPreparationInformation ::=	SEQUENCE {
	criticalExtensions					CHOICE {
		c1									CHOICE{
			handoverPreparationInformation-r8	HandoverPreparationInformation-r8-IEs,
			spare7 NULL,
			spare6 NULL, spare5 NULL, spare4 NULL,
			spare3 NULL, spare2 NULL, spare1 NULL
		},
		criticalExtensionsFuture			SEQUENCE {}
	}
}

HandoverPreparationInformation-r8-IEs ::= SEQUENCE {
	ue-RadioAccessCapabilityInfo		UE-CapabilityRAT-ContainerList,
	as-Config							AS-Config					OPTIONAL, 		-- Cond HO
	rrm-Config							RRM-Config					OPTIONAL,
	as-Context							AS-Context				OPTIONAL, 		-- Cond HO
	nonCriticalExtension				HandoverPreparationInformation-v920-IEs		OPTIONAL
}

HandoverPreparationInformation-v920-IEs	::= SEQUENCE {
	ue-ConfigRelease-r9					ENUMERATED {
										rel9, rel10, rel11, rel12, v10j0, v11e0,
										v1280, spare1, ...} 			OPTIONAL, 	-- Cond HO2
	nonCriticalExtension				HandoverPreparationInformation-v9d0-IEs		OPTIONAL
}

HandoverPreparationInformation-v9d0-IEs	::= SEQUENCE {
	lateNonCriticalExtension			OCTET STRING (CONTAINING HandoverPreparationInformation-v9j0-IEs)	OPTIONAL,
	nonCriticalExtension				HandoverPreparationInformation-v9e0-IEs			OPTIONAL
}

-- Late non-critical extensions:
HandoverPreparationInformation-v9j0-IEs ::= SEQUENCE {
	-- Following field is only for pre REL-10 late non-critical extensions
	lateNonCriticalExtension			OCTET STRING					OPTIONAL,
	nonCriticalExtension				HandoverPreparationInformation-v10j0-IEs		OPTIONAL
}

HandoverPreparationInformation-v10j0-IEs ::= SEQUENCE {
	as-Config-v10j0						AS-Config-v10j0			OPTIONAL,
	-- Following field is only for late non-critical extensions from REL-10
	nonCriticalExtension				SEQUENCE {}				OPTIONAL
}

-- Regular non-critical extensions:
HandoverPreparationInformation-v9e0-IEs	::= SEQUENCE {
	as-Config-v9e0						AS-Config-v9e0					OPTIONAL,	-- Cond HO2
	nonCriticalExtension				HandoverPreparationInformation-v1130-IEs		OPTIONAL
}

HandoverPreparationInformation-v1130-IEs	::= SEQUENCE {
	as-Context-v1130					AS-Context-v1130				OPTIONAL,	-- Cond HO2
	nonCriticalExtension				HandoverPreparationInformation-v1250-IEs						OPTIONAL
}

HandoverPreparationInformation-v1250-IEs ::= SEQUENCE {
	ue-SupportedEARFCN-r12 				ARFCN-ValueEUTRA-r9				OPTIONAL,	-- Cond HO3
	as-Config-v1250					AS-Config-v1250				OPTIONAL, 	-- Cond HO2 
	nonCriticalExtension				SEQUENCE {}						OPTIONAL
}

-- ASN1STOP

SCG-Config-r12 ::=					SEQUENCE {
	criticalExtensions					CHOICE {
		c1									CHOICE{
			scg-Config-r12					SCG-Config-r12-IEs,
			spare7 NULL,
			spare6 NULL, spare5 NULL, spare4 NULL,
			spare3 NULL, spare2 NULL, spare1 NULL
		},
		criticalExtensionsFuture			SEQUENCE {}
	}
}

SCG-Config-r12-IEs ::=				SEQUENCE {
	scg-RadioConfig-r12					SCG-ConfigPartSCG-r12				OPTIONAL,
	nonCriticalExtension				SEQUENCE {}							OPTIONAL
}

-- ASN1STOP

SCG-ConfigInfo-r12 ::=					SEQUENCE {
	criticalExtensions					CHOICE {
		c1									CHOICE{
			scg-ConfigInfo-r12					SCG-ConfigInfo-r12-IEs,
			spare7 NULL,
			spare6 NULL, spare5 NULL, spare4 NULL,
			spare3 NULL, spare2 NULL, spare1 NULL
		},
		criticalExtensionsFuture			SEQUENCE {}
	}
}

SCG-ConfigInfo-r12-IEs ::=			SEQUENCE {
	radioResourceConfigDedMCG-r12	RadioResourceConfigDedicated		OPTIONAL,
	sCellToAddModListMCG-r12		SCellToAddModList-r10				OPTIONAL,
	measGapConfig-r12				MeasGapConfig						OPTIONAL,
	powerCoordinationInfo-r12		PowerCoordinationInfo-r12			OPTIONAL,
	scg-RadioConfig-r12				SCG-ConfigPartSCG-r12				OPTIONAL,
	eutra-CapabilityInfo-r12		OCTET STRING (CONTAINING UECapabilityInformation)	OPTIONAL,
	scg-ConfigRestrictInfo-r12		SCG-ConfigRestrictInfo-r12			OPTIONAL,
	mbmsInterestIndication-r12		OCTET STRING (CONTAINING
										MBMSInterestIndication-r11)		OPTIONAL,
	measResultServCellListSCG-r12	MeasResultServCellListSCG-r12		OPTIONAL,
	drb-ToAddModListSCG-r12			DRB-InfoListSCG-r12					OPTIONAL,
	drb-ToReleaseListSCG-r12		DRB-ToReleaseList					OPTIONAL,
	sCellToAddModListSCG-r12		SCellToAddModListSCG-r12			OPTIONAL,
	sCellToReleaseListSCG-r12		SCellToReleaseList-r10				OPTIONAL,
	p-Max-r12							P-Max								OPTIONAL,
	nonCriticalExtension			SCG-ConfigInfo-v13x0-IEs			OPTIONAL
}

SCG-ConfigInfo-v13x0-IEs ::=		SEQUENCE {
	measResultSSTD-r13				MeasResultSSTD-r13					OPTIONAL,	sCellToAddModListMCG-Ext-r13		SCellToAddModListExt-r13			OPTIONAL,
	measResultServCellListSCG-Ext-r13	MeasResultServCellListSCG-Ext-r13	OPTIONAL,
	sCellToAddModListSCG-Ext-r13		SCellToAddModListSCG-Ext-r13			OPTIONAL,
	sCellToReleaseListSCG-Ext-r13	SCellToReleaseListExt-r13			OPTIONAL,
	nonCriticalExtension			SEQUENCE {}							OPTIONAL
}

DRB-InfoListSCG-r12 ::=				SEQUENCE (SIZE (1..maxDRB)) OF DRB-InfoSCG-r12

DRB-InfoSCG-r12 ::=				SEQUENCE {
	eps-BearerIdentity-r12			INTEGER (0..15)				OPTIONAL,	-- Cond DRB-Setup
	drb-Identity-r12				DRB-Identity,
	drb-Type-r12					ENUMERATED {split, scg}		OPTIONAL,	-- Cond DRB-Setup
	...
}

SCellToAddModListSCG-r12 ::=	SEQUENCE (SIZE (1..maxSCell-r10)) OF Cell-ToAddMod-r12

SCellToAddModListSCG-Ext-r13 ::=	SEQUENCE (SIZE (maxSCell-Plus1..maxSCell-r13)) OF Cell-ToAddMod-r12

Cell-ToAddMod-r12 ::=				SEQUENCE {
	sCellIndex-r12						SCellIndex-r10,
	cellIdentification-r12				SEQUENCE {
		physCellId-r12						PhysCellId,
		dl-CarrierFreq-r12					ARFCN-ValueEUTRA-r9
	}																OPTIONAL,	-- Cond SCellAdd
	measResultCellToAdd-r12				SEQUENCE {
		rsrpResult-r12						RSRP-Range,
		rsrqResult-r12						RSRQ-Range
	}																OPTIONAL,	-- Cond SCellAdd2
--	...,
	[[		sCellIndex-r13					SCellIndex-r13				OPTIONAL,
		measResultCellToAdd-v13xy			SEQUENCE {
			rs-sinrResult-r13					RS-SINR-Range-r13
		}															OPTIONAL	-- Cond SCellAdd2
	]]
}

MeasResultServCellListSCG-r12 ::=	SEQUENCE (SIZE (1..maxServCell-r10)) OF MeasResultServCellSCG-r12

MeasResultServCellListSCG-Ext-r13 ::=	SEQUENCE (SIZE (maxServCell-Plus1..maxServCell-r13)) OF MeasResultServCellSCG-r12

MeasResultServCellSCG-r12 ::=			SEQUENCE {
	servCellId-r12						ServCellIndex-r10,
	measResultSCell-r12					SEQUENCE {
		rsrpResultSCell-r12					RSRP-Range,
		rsrqResultSCell-r12					RSRQ-Range
	},
--	...,
	[[		servCellId-r13						ServCellIndexFull-r13		OPTIONAL,
		measResultSCell-v13xy				SEQUENCE {
			rs-sinrResultSCell-r13				RS-SINR-Range-r13
		}															OPTIONAL
	]]
}

SCG-ConfigRestrictInfo-r12 ::=		SEQUENCE {
	maxSCH-TB-BitsDL-r12				INTEGER (1..100),
	maxSCH-TB-BitsUL-r12				INTEGER (1..100)
}

-- ASN1STOP

UERadioAccessCapabilityInformation ::= SEQUENCE {
	criticalExtensions					CHOICE {
		c1									CHOICE{
			ueRadioAccessCapabilityInformation-r8
												UERadioAccessCapabilityInformation-r8-IEs,
			spare7 NULL,
			spare6 NULL, spare5 NULL, spare4 NULL,
			spare3 NULL, spare2 NULL, spare1 NULL
		},
		criticalExtensionsFuture			SEQUENCE {}
	}
}

UERadioAccessCapabilityInformation-r8-IEs ::= SEQUENCE {
	ue-RadioAccessCapabilityInfo		OCTET STRING (CONTAINING UECapabilityInformation),
	nonCriticalExtension				SEQUENCE {}							OPTIONAL
}

-- ASN1STOP

UERadioPagingInformation ::= SEQUENCE {
	criticalExtensions					CHOICE {
		c1									CHOICE{
			ueRadioPagingInformation-r12			UERadioPagingInformation-r12-IEs,
			spare7 NULL,
			spare6 NULL, spare5 NULL, spare4 NULL,
			spare3 NULL, spare2 NULL, spare1 NULL
		},
		criticalExtensionsFuture			SEQUENCE {}
	}
}

UERadioPagingInformation-r12-IEs ::= SEQUENCE {
	ue-RadioPagingInfo-r12				OCTET STRING (CONTAINING UE-RadioPagingInfo-r12),
	nonCriticalExtension				UERadioPagingInformation-v13xy-IEs			OPTIONAL
}

UERadioPagingInformation-v13xy-IEs ::= SEQUENCE {
	supportedBandListEUTRAForPaging-r13		SEQUENCE (SIZE (1..maxBands)) OF FreqBandIndicator-r11 OPTIONAL,
	nonCriticalExtension					SEQUENCE {}								OPTIONAL

}

-- ASN1STOP

AS-Config ::=				SEQUENCE {
	sourceMeasConfig					MeasConfig,
	sourceRadioResourceConfig			RadioResourceConfigDedicated,
	sourceSecurityAlgorithmConfig		SecurityAlgorithmConfig,
	sourceUE-Identity					C-RNTI,
	sourceMasterInformationBlock		MasterInformationBlock,
	sourceSystemInformationBlockType1	SystemInformationBlockType1(WITH COMPONENTS
											{..., nonCriticalExtension ABSENT}),
	sourceSystemInformationBlockType2	SystemInformationBlockType2,
	antennaInfoCommon					AntennaInfoCommon,
	sourceDl-CarrierFreq				ARFCN-ValueEUTRA,
--	...,
	[[	sourceSystemInformationBlockType1Ext	OCTET STRING (CONTAINING
												SystemInformationBlockType1-v890-IEs)	OPTIONAL,
		sourceOtherConfig-r9				OtherConfig-r9
	-- sourceOtherConfig-r9 should have been optional. A target eNB compliant with this transfer
	-- syntax should support receiving an AS-Config not including this extension addition group
	-- e.g. from a legacy source eNB
	]],
	[[	sourceSCellConfigList-r10			SCellToAddModList-r10			OPTIONAL
	]],
	[[	sourceConfigSCG-r12					SCG-Config-r12		OPTIONAL
	]]
}

AS-Config-v9e0 ::=				SEQUENCE {
	sourceDl-CarrierFreq-v9e0		ARFCN-ValueEUTRA-v9e0
}

AS-Config-v10j0 ::=				SEQUENCE {
	antennaInfoDedicatedPCell-v10i0		AntennaInfoDedicated-v10i0			OPTIONAL
}

AS-Config-v1250 ::=				SEQUENCE {
	sourceWlan-OffloadConfig-r12		WLAN-OffloadConfig-r12				OPTIONAL,
	sourceSL-CommConfig-r12				SL-CommConfig-r12					OPTIONAL,
	sourceSL-DiscConfig-r12				SL-DiscConfig-r12					OPTIONAL
}

-- ASN1STOP

AS-Context ::=							SEQUENCE {
	reestablishmentInfo						ReestablishmentInfo			OPTIONAL	-- Cond HO
}

AS-Context-v1130 ::=					SEQUENCE {
	idc-Indication-r11						OCTET STRING (CONTAINING
											InDeviceCoexIndication-r11)	OPTIONAL,	-- Cond HO2
	mbmsInterestIndication-r11				OCTET STRING (CONTAINING
											MBMSInterestIndication-r11)	OPTIONAL,	-- Cond HO2
	powerPrefIndication-r11					OCTET STRING (CONTAINING
											UEAssistanceInformation-r11)	OPTIONAL,	-- Cond HO2
--	...,
	[[	sidelinkUEInformation-r12				OCTET STRING (CONTAINING
												SidelinkUEInformation-r12)	OPTIONAL	-- Cond HO2
	]]
}

-- ASN1STOP

ReestablishmentInfo ::=				SEQUENCE {
	sourcePhysCellId					PhysCellId,
	targetCellShortMAC-I				ShortMAC-I,
	additionalReestabInfoList			AdditionalReestabInfoList				OPTIONAL,
	...
}

AdditionalReestabInfoList ::=		SEQUENCE ( SIZE (1..maxReestabInfo) ) OF AdditionalReestabInfo

AdditionalReestabInfo ::=	SEQUENCE{
	cellIdentity						CellIdentity,
	key-eNodeB-Star					Key-eNodeB-Star,
	shortMAC-I							ShortMAC-I
}

Key-eNodeB-Star ::=					BIT STRING (SIZE (256))

-- ASN1STOP

RRM-Config ::=				SEQUENCE {
	ue-InactiveTime				ENUMERATED {
									s1, s2, s3, s5, s7, s10, s15, s20,
									s25, s30, s40, s50, min1, min1s20c, min1s40,
									min2, min2s30, min3, min3s30, min4, min5, min6,
									min7, min8, min9, min10, min12, min14, min17, min20,
									min24, min28, min33, min38, min44, min50, hr1,
									hr1min30, hr2, hr2min30, hr3, hr3min30, hr4, hr5, hr6,
									hr8, hr10, hr13, hr16, hr20, day1, day1hr12, day2,
									day2hr12, day3, day4, day5, day7, day10, day14, day19,
									day24, day30, dayMoreThan30}		OPTIONAL,
--	...,
	[[	candidateCellInfoList-r10	CandidateCellInfoList-r10		OPTIONAL
	]]
}

CandidateCellInfoList-r10 ::=	SEQUENCE (SIZE (1..maxFreq)) OF CandidateCellInfo-r10

CandidateCellInfo-r10 ::=		SEQUENCE {
	-- cellIdentification
	physCellId-r10					PhysCellId,
	dl-CarrierFreq-r10				ARFCN-ValueEUTRA,
	-- available measurement results
	rsrpResult-r10					RSRP-Range			OPTIONAL,
	rsrqResult-r10					RSRQ-Range			OPTIONAL,
--	...,
	[[	dl-CarrierFreq-v1090			ARFCN-ValueEUTRA-v9e0		OPTIONAL
	]],
	[[	rsrqResult-v1250				RSRQ-Range-v1250			OPTIONAL
	]],
	[[	rs-sinrResult-v13xy				RS-SINR-Range-r13			OPTIONAL
	]]
}

-- ASN1STOP

maxReestabInfo				INTEGER ::= 32	-- Maximum number of KeNB* and shortMAC-I forwarded
											-- at handover for re-establishment preparation

-- ASN1STOP

END

-- ASN1STOP
