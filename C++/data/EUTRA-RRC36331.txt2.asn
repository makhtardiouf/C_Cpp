EUTRA-RRC-Definitions DEFINITIONS AUTOMATIC TAGS ::=

BEGIN

-- ASN1STOP

BCCH-BCH-Message ::= [UNIVERSAL 16] IMPLICIT NULL 
	message					BCCH-BCH-MessageType


BCCH-BCH-MessageType ::=						MasterInformationBlock

-- ASN1STOP

BCCH-DL-SCH-Message ::= [UNIVERSAL 16] IMPLICIT NULL {
	message					BCCH-DL-SCH-MessageType
}

BCCH-DL-SCH-MessageType ::= CHOICE {
	c1						CHOICE {
		systemInformation						SystemInformation,
		systemInformationBlockType1				SystemInformationBlockType1
	},
	messageClassExtension	[UNIVERSAL 16] IMPLICIT NULL {}
}

-- ASN1STOP

MCCH-Message ::= 		[UNIVERSAL 16] IMPLICIT NULL {
	message					MCCH-MessageType
}

MCCH-MessageType ::= CHOICE {
	c1							CHOICE {
		mbsfnAreaConfiguration-r9		MBSFNAreaConfiguration-r9
	},
	later						CHOICE {
		c2								CHOICE{
			mbmsCountingRequest-r10			MBMSCountingRequest-r10
		},
		messageClassExtension	[UNIVERSAL 16] IMPLICIT NULL {}
	}
}

-- ASN1STOP

PCCH-Message ::= [UNIVERSAL 16] IMPLICIT NULL {
	message					PCCH-MessageType
}

PCCH-MessageType ::= CHOICE {
	c1						CHOICE {
		paging									Paging
	},
	messageClassExtension	[UNIVERSAL 16] IMPLICIT NULL {}
}

-- ASN1STOP

DL-CCCH-Message ::= [UNIVERSAL 16] IMPLICIT NULL {
	message					DL-CCCH-MessageType
}

DL-CCCH-MessageType ::= CHOICE {
	c1						CHOICE {
		rrcConnectionReestablishment			RRCConnectionReestablishment,
		rrcConnectionReestablishmentReject		RRCConnectionReestablishmentReject,
		rrcConnectionReject						RRCConnectionReject,
		rrcConnectionSetup						RRCConnectionSetup
	},
	messageClassExtension	[UNIVERSAL 16] IMPLICIT NULL {}
}

-- ASN1STOP

DL-DCCH-Message ::= [UNIVERSAL 16] IMPLICIT NULL {
	message					DL-DCCH-MessageType
}

DL-DCCH-MessageType ::= CHOICE {
	c1						CHOICE {
		csfbParametersResponseCDMA2000			CSFBParametersResponseCDMA2000,
		dlInformationTransfer					DLInformationTransfer,
		handoverFromEUTRAPreparationRequest		HandoverFromEUTRAPreparationRequest,
		mobilityFromEUTRACommand				MobilityFromEUTRACommand,
		rrcConnectionReconfiguration			RRCConnectionReconfiguration,
		rrcConnectionRelease					RRCConnectionRelease,
		securityModeCommand						SecurityModeCommand,
		ueCapabilityEnquiry						UECapabilityEnquiry,
		counterCheck							CounterCheck,
		ueInformationRequest-r9					UEInformationRequest-r9,
		loggedMeasurementConfiguration-r10		LoggedMeasurementConfiguration-r10,
		rnReconfiguration-r10					RNReconfiguration-r10,
		spare4 NULL,
		spare3 NULL, spare2 NULL, spare1 NULL
	},
	messageClassExtension	[UNIVERSAL 16] IMPLICIT NULL {}
}

-- ASN1STOP

UL-CCCH-Message ::= [UNIVERSAL 16] IMPLICIT NULL {
	message					UL-CCCH-MessageType
}

UL-CCCH-MessageType ::= CHOICE {
	c1						CHOICE {
		rrcConnectionReestablishmentRequest		RRCConnectionReestablishmentRequest,
		rrcConnectionRequest					RRCConnectionRequest
	},
	messageClassExtension	[UNIVERSAL 16] IMPLICIT NULL {}
}

-- ASN1STOP

UL-DCCH-Message ::= [UNIVERSAL 16] IMPLICIT NULL {
	message					UL-DCCH-MessageType
}

UL-DCCH-MessageType ::= CHOICE {
	c1						CHOICE {
		csfbParametersRequestCDMA2000			CSFBParametersRequestCDMA2000,
		measurementReport						MeasurementReport,
		rrcConnectionReconfigurationComplete	RRCConnectionReconfigurationComplete,
		rrcConnectionReestablishmentComplete	RRCConnectionReestablishmentComplete,
		rrcConnectionSetupComplete				RRCConnectionSetupComplete,
		securityModeComplete					SecurityModeComplete,
		securityModeFailure						SecurityModeFailure,
		ueCapabilityInformation					UECapabilityInformation,
		ulHandoverPreparationTransfer			ULHandoverPreparationTransfer,
		ulInformationTransfer					ULInformationTransfer,
		counterCheckResponse					CounterCheckResponse,
		ueInformationResponse-r9				UEInformationResponse-r9,
		proximityIndication-r9					ProximityIndication-r9,
		rnReconfigurationComplete-r10			RNReconfigurationComplete-r10,
		mbmsCountingResponse-r10				MBMSCountingResponse-r10,
		interFreqRSTDMeasurementIndication-r10	InterFreqRSTDMeasurementIndication-r10
	},
	messageClassExtension	CHOICE {
		c2							CHOICE {
			ueAssistanceInformation-r11			UEAssistanceInformation-r11,
			inDeviceCoexIndication-r11			InDeviceCoexIndication-r11,
			mbmsInterestIndication-r11			MBMSInterestIndication-r11,
			scgFailureInformation-r12			SCGFailureInformation-r12,
			sidelinkUEInformation-r12			SidelinkUEInformation-r12,
			spare11 NULL, spare10 NULL,
			spare9 NULL, spare8 NULL, spare7 NULL,
			spare6 NULL, spare5 NULL, spare4 NULL,
			spare3 NULL, spare2 NULL, spare1 NULL
		},
		messageClassExtensionFuture-r11	[UNIVERSAL 16] IMPLICIT NULL {}
	}
}

-- ASN1STOP

SC-MCCH-Message ::= [UNIVERSAL 16] IMPLICIT NULL {
	message					SC-MCCH-MessageType
}


SC-MCCH-MessageType ::= CHOICE {
	c1						CHOICE {
		scptmConfiguration-r13						SCPTMConfiguration-r13
	},
	messageClassExtension	[UNIVERSAL 16] IMPLICIT NULL {}
}

-- ASN1STOP

CounterCheck ::=			[UNIVERSAL 16] IMPLICIT NULL {
	rrc-TransactionIdentifier			RRC-TransactionIdentifier,
	criticalExtensions					CHOICE {
		c1									CHOICE {
			counterCheck-r8						CounterCheck-r8-IEs,
			spare3 NULL, spare2 NULL, spare1 NULL
		},
		criticalExtensionsFuture			[UNIVERSAL 16] IMPLICIT NULL {}
	}
}

CounterCheck-r8-IEs ::=	[UNIVERSAL 16] IMPLICIT NULL {
	drb-CountMSB-InfoList				DRB-CountMSB-InfoList,
	nonCriticalExtension				CounterCheck-v8a0-IEs				OPTIONAL
}

CounterCheck-v8a0-IEs ::= [UNIVERSAL 16] IMPLICIT NULL {
	lateNonCriticalExtension			OCTET STRING						OPTIONAL,
	nonCriticalExtension				[UNIVERSAL 16] IMPLICIT NULL {}							OPTIONAL
}

DRB-CountMSB-InfoList ::=		[UNIVERSAL 16] IMPLICIT NULL (SIZE (1..maxDRB)) OF DRB-CountMSB-Info

DRB-CountMSB-Info ::=	[UNIVERSAL 16] IMPLICIT NULL {
	drb-Identity					DRB-Identity,
	countMSB-Uplink					INTEGER(0..33554431),
	countMSB-Downlink				INTEGER(0..33554431)
}

-- ASN1STOP

CounterCheckResponse ::=			[UNIVERSAL 16] IMPLICIT NULL {
	rrc-TransactionIdentifier			RRC-TransactionIdentifier,
	criticalExtensions					CHOICE {
		counterCheckResponse-r8				CounterCheckResponse-r8-IEs,
		criticalExtensionsFuture			[UNIVERSAL 16] IMPLICIT NULL {}
	}
}

CounterCheckResponse-r8-IEs ::=	[UNIVERSAL 16] IMPLICIT NULL {
	drb-CountInfoList					DRB-CountInfoList,
	nonCriticalExtension				CounterCheckResponse-v8a0-IEs		OPTIONAL
}

CounterCheckResponse-v8a0-IEs ::= [UNIVERSAL 16] IMPLICIT NULL {
	lateNonCriticalExtension			OCTET STRING						OPTIONAL,
	nonCriticalExtension				[UNIVERSAL 16] IMPLICIT NULL {}							OPTIONAL
}

DRB-CountInfoList ::=			[UNIVERSAL 16] IMPLICIT NULL (SIZE (0..maxDRB)) OF DRB-CountInfo

DRB-CountInfo ::=	[UNIVERSAL 16] IMPLICIT NULL {
	drb-Identity					DRB-Identity,
	count-Uplink					INTEGER(0..4294967295),
	count-Downlink					INTEGER(0..4294967295)
}

-- ASN1STOP

CSFBParametersRequestCDMA2000 ::= [UNIVERSAL 16] IMPLICIT NULL {
	criticalExtensions					CHOICE {
		csfbParametersRequestCDMA2000-r8	CSFBParametersRequestCDMA2000-r8-IEs,
		criticalExtensionsFuture			[UNIVERSAL 16] IMPLICIT NULL {}
	}
}

CSFBParametersRequestCDMA2000-r8-IEs ::= [UNIVERSAL 16] IMPLICIT NULL {
	nonCriticalExtension				CSFBParametersRequestCDMA2000-v8a0-IEs	OPTIONAL
}

CSFBParametersRequestCDMA2000-v8a0-IEs ::= [UNIVERSAL 16] IMPLICIT NULL {
	lateNonCriticalExtension			OCTET STRING						OPTIONAL,
	nonCriticalExtension				[UNIVERSAL 16] IMPLICIT NULL {}							OPTIONAL
}

-- ASN1STOP

CSFBParametersResponseCDMA2000 ::= [UNIVERSAL 16] IMPLICIT NULL {
	rrc-TransactionIdentifier			RRC-TransactionIdentifier,
	criticalExtensions						CHOICE {
		csfbParametersResponseCDMA2000-r8		CSFBParametersResponseCDMA2000-r8-IEs,
		criticalExtensionsFuture				[UNIVERSAL 16] IMPLICIT NULL {}
	}
}

CSFBParametersResponseCDMA2000-r8-IEs ::= [UNIVERSAL 16] IMPLICIT NULL {
	rand								RAND-CDMA2000,
	mobilityParameters					MobilityParametersCDMA2000,
	nonCriticalExtension				CSFBParametersResponseCDMA2000-v8a0-IEs	OPTIONAL
}

CSFBParametersResponseCDMA2000-v8a0-IEs ::= [UNIVERSAL 16] IMPLICIT NULL {
	lateNonCriticalExtension			OCTET STRING						OPTIONAL,
	nonCriticalExtension				[UNIVERSAL 16] IMPLICIT NULL {}							OPTIONAL
}

-- ASN1STOP

DLInformationTransfer ::=			[UNIVERSAL 16] IMPLICIT NULL {
	rrc-TransactionIdentifier			RRC-TransactionIdentifier,
	criticalExtensions					CHOICE {
		c1									CHOICE {
			dlInformationTransfer-r8			DLInformationTransfer-r8-IEs,
			spare3 NULL, spare2 NULL, spare1 NULL
		},
		criticalExtensionsFuture			[UNIVERSAL 16] IMPLICIT NULL {}
	}
}

DLInformationTransfer-r8-IEs ::=	[UNIVERSAL 16] IMPLICIT NULL {
	dedicatedInfoType					CHOICE {
		dedicatedInfoNAS					DedicatedInfoNAS,
		dedicatedInfoCDMA2000-1XRTT			DedicatedInfoCDMA2000,
		dedicatedInfoCDMA2000-HRPD			DedicatedInfoCDMA2000
	},
	nonCriticalExtension				DLInformationTransfer-v8a0-IEs		OPTIONAL
}

DLInformationTransfer-v8a0-IEs ::= [UNIVERSAL 16] IMPLICIT NULL {
	lateNonCriticalExtension			OCTET STRING						OPTIONAL,
	nonCriticalExtension				[UNIVERSAL 16] IMPLICIT NULL {}							OPTIONAL
}

-- ASN1STOP

HandoverFromEUTRAPreparationRequest ::= [UNIVERSAL 16] IMPLICIT NULL {
	rrc-TransactionIdentifier		RRC-TransactionIdentifier,
	criticalExtensions					CHOICE {
		c1									CHOICE {
			handoverFromEUTRAPreparationRequest-r8
												HandoverFromEUTRAPreparationRequest-r8-IEs,
			spare3 NULL, spare2 NULL, spare1 NULL
		},
		criticalExtensionsFuture			[UNIVERSAL 16] IMPLICIT NULL {}
	}
}

HandoverFromEUTRAPreparationRequest-r8-IEs ::= [UNIVERSAL 16] IMPLICIT NULL {
	cdma2000-Type					CDMA2000-Type,
	rand							RAND-CDMA2000				OPTIONAL,	-- Cond cdma2000-Type
	mobilityParameters				MobilityParametersCDMA2000	OPTIONAL,	-- Cond cdma2000-Type
	nonCriticalExtension			HandoverFromEUTRAPreparationRequest-v890-IEs	OPTIONAL
}

HandoverFromEUTRAPreparationRequest-v890-IEs ::= [UNIVERSAL 16] IMPLICIT NULL {
	lateNonCriticalExtension		OCTET STRING				OPTIONAL,
	nonCriticalExtension			HandoverFromEUTRAPreparationRequest-v920-IEs	OPTIONAL
}

HandoverFromEUTRAPreparationRequest-v920-IEs ::= [UNIVERSAL 16] IMPLICIT NULL {
	concurrPrepCDMA2000-HRPD-r9		BOOLEAN					OPTIONAL,	-- Cond cdma2000-Type
	nonCriticalExtension			HandoverFromEUTRAPreparationRequest-v1020-IEs	OPTIONAL
}

HandoverFromEUTRAPreparationRequest-v1020-IEs ::= [UNIVERSAL 16] IMPLICIT NULL {
	dualRxTxRedirectIndicator-r10		ENUMERATED {true}		OPTIONAL,	-- Cond cdma2000-1XRTT
	redirectCarrierCDMA2000-1XRTT-r10	CarrierFreqCDMA2000		OPTIONAL,	-- Cond dualRxTxRedirect
	nonCriticalExtension				[UNIVERSAL 16] IMPLICIT NULL {}				OPTIONAL
}

-- ASN1STOP

InDeviceCoexIndication-r11 ::=		[UNIVERSAL 16] IMPLICIT NULL {
	criticalExtensions					CHOICE {
		c1									CHOICE {
			inDeviceCoexIndication-r11				InDeviceCoexIndication-r11-IEs,
			spare3 NULL, spare2 NULL, spare1 NULL
		},
		criticalExtensionsFuture			[UNIVERSAL 16] IMPLICIT NULL {}
	}
}

InDeviceCoexIndication-r11-IEs ::=	[UNIVERSAL 16] IMPLICIT NULL {
	affectedCarrierFreqList-r11			AffectedCarrierFreqList-r11					OPTIONAL,
	tdm-AssistanceInfo-r11				TDM-AssistanceInfo-r11						OPTIONAL,
	lateNonCriticalExtension			OCTET STRING								OPTIONAL,
	nonCriticalExtension				InDeviceCoexIndication-v11d0-IEs			OPTIONAL
}

InDeviceCoexIndication-v11d0-IEs ::=	[UNIVERSAL 16] IMPLICIT NULL {
	ul-CA-AssistanceInfo-r11			[UNIVERSAL 16] IMPLICIT NULL {
		affectedCarrierFreqCombList-r11	AffectedCarrierFreqCombList-r11			OPTIONAL, 
		victimSystemType-r11				VictimSystemType-r11
	}																			OPTIONAL,
	nonCriticalExtension				[UNIVERSAL 16] IMPLICIT NULL {}								OPTIONAL
}

AffectedCarrierFreqList-r11 ::=	[UNIVERSAL 16] IMPLICIT NULL (SIZE (1..maxFreqIDC-r11)) OF AffectedCarrierFreq-r11

AffectedCarrierFreq-r11 ::=	[UNIVERSAL 16] IMPLICIT NULL {
	carrierFreq-r11				MeasObjectId,
	interferenceDirection-r11	ENUMERATED {eutra, other, both, spare}
}

AffectedCarrierFreqCombList-r11 ::=	[UNIVERSAL 16] IMPLICIT NULL (SIZE (1..maxCombIDC-r11)) OF AffectedCarrierFreqComb-r11

AffectedCarrierFreqComb-r11 ::=	[UNIVERSAL 16] IMPLICIT NULL (SIZE (2..maxServCell-r10)) OF MeasObjectId

TDM-AssistanceInfo-r11 ::=	CHOICE {
	drx-AssistanceInfo-r11				[UNIVERSAL 16] IMPLICIT NULL {
		drx-CycleLength-r11					ENUMERATED {sf40, sf64, sf80, sf128, sf160,
												 sf256, spare2, spare1},
		drx-Offset-r11						INTEGER (0..255)	OPTIONAL,
		drx-ActiveTime-r11					ENUMERATED {sf20, sf30, sf40, sf60, sf80,
												 sf100, spare2, spare1}
	},
	idc-SubframePatternList-r11			IDC-SubframePatternList-r11,
	...
}

IDC-SubframePatternList-r11 ::=	[UNIVERSAL 16] IMPLICIT NULL (SIZE (1..maxSubframePatternIDC-r11)) OF IDC-SubframePattern-r11

IDC-SubframePattern-r11 ::= CHOICE {
	subframePatternFDD-r11				BIT STRING (SIZE (4)),
	subframePatternTDD-r11				CHOICE {
		subframeConfig0-r11					BIT STRING (SIZE (70)),
		subframeConfig1-5-r11				BIT STRING (SIZE (10)),
		subframeConfig6-r11					BIT STRING (SIZE (60))
	},
	...
}

VictimSystemType-r11 ::= [UNIVERSAL 16] IMPLICIT NULL {
	gps-r11 							ENUMERATED {true}				OPTIONAL,
	glonass-r11							ENUMERATED {true}				OPTIONAL,
	bds-r11								ENUMERATED {true}				OPTIONAL,
	galileo-r11 						ENUMERATED {true}				OPTIONAL,
	wlan-r11							ENUMERATED {true}				OPTIONAL,
	bluetooth-r11						ENUMERATED {true}				OPTIONAL
}

-- ASN1STOP

InterFreqRSTDMeasurementIndication-r10 ::=			[UNIVERSAL 16] IMPLICIT NULL {
	criticalExtensions					CHOICE {
		c1									CHOICE {
			interFreqRSTDMeasurementIndication-r10	InterFreqRSTDMeasurementIndication-r10-IEs,
			spare3 NULL, spare2 NULL, spare1 NULL
		},
		criticalExtensionsFuture			[UNIVERSAL 16] IMPLICIT NULL {}
	}
}

InterFreqRSTDMeasurementIndication-r10-IEs ::=		[UNIVERSAL 16] IMPLICIT NULL {
	rstd-InterFreqIndication-r10		CHOICE {
		start								[UNIVERSAL 16] IMPLICIT NULL {
			rstd-InterFreqInfoList-r10				RSTD-InterFreqInfoList-r10
		},
		stop								NULL
	},
	lateNonCriticalExtension			OCTET STRING						OPTIONAL,
	nonCriticalExtension				[UNIVERSAL 16] IMPLICIT NULL {}							OPTIONAL
}

RSTD-InterFreqInfoList-r10 ::=	[UNIVERSAL 16] IMPLICIT NULL (SIZE(1..maxRSTD-Freq-r10)) OF RSTD-InterFreqInfo-r10

RSTD-InterFreqInfo-r10 ::=		[UNIVERSAL 16] IMPLICIT NULL {
	carrierFreq-r10					ARFCN-ValueEUTRA,
	measPRS-Offset-r10				INTEGER (0..39)
--	,
----	...,
--	[[	carrierFreq-v1090			ARFCN-ValueEUTRA-v9e0				OPTIONAL
--	]]
}

-- ASN1STOP

LoggedMeasurementConfiguration-r10 ::=	[UNIVERSAL 16] IMPLICIT NULL {
	criticalExtensions					CHOICE {
		c1									CHOICE {
			loggedMeasurementConfiguration-r10		LoggedMeasurementConfiguration-r10-IEs,
			spare3 NULL, spare2 NULL, spare1 NULL
		},
		criticalExtensionsFuture				[UNIVERSAL 16] IMPLICIT NULL {}
	}
}


LoggedMeasurementConfiguration-r10-IEs ::= [UNIVERSAL 16] IMPLICIT NULL {		
	traceReference-r10				TraceReference-r10,
	traceRecordingSessionRef-r10	OCTET STRING (SIZE (2)),
	tce-Id-r10						OCTET STRING (SIZE (1)),
	absoluteTimeInfo-r10			AbsoluteTimeInfo-r10,
	areaConfiguration-r10			AreaConfiguration-r10		OPTIONAL,	-- Need OR
	loggingDuration-r10				LoggingDuration-r10,
	loggingInterval-r10				LoggingInterval-r10,
	nonCriticalExtension			LoggedMeasurementConfiguration-v1080-IEs	OPTIONAL
}

LoggedMeasurementConfiguration-v1080-IEs ::= [UNIVERSAL 16] IMPLICIT NULL {
	lateNonCriticalExtension-r10	OCTET STRING						OPTIONAL,
	nonCriticalExtension			LoggedMeasurementConfiguration-v1130-IEs	OPTIONAL
}

LoggedMeasurementConfiguration-v1130-IEs ::= [UNIVERSAL 16] IMPLICIT NULL {
	plmn-IdentityList-r11			PLMN-IdentityList3-r11		OPTIONAL,	-- Need OR
	areaConfiguration-v1130			AreaConfiguration-v1130		OPTIONAL,	-- Need OR
	nonCriticalExtension			LoggedMeasurementConfiguration-v1250-IEs	OPTIONAL
}

LoggedMeasurementConfiguration-v1250-IEs ::= [UNIVERSAL 16] IMPLICIT NULL {
	targetMBSFN-AreaList-r12	TargetMBSFN-AreaList-r12		OPTIONAL,	-- Need OP
	nonCriticalExtension			[UNIVERSAL 16] IMPLICIT NULL {}					OPTIONAL
}

TargetMBSFN-AreaList-r12 ::= 			[UNIVERSAL 16] IMPLICIT NULL (SIZE (0..maxMBSFN-Area)) OF TargetMBSFN-Area-r12

TargetMBSFN-Area-r12 ::=				[UNIVERSAL 16] IMPLICIT NULL {
	mbsfn-AreaId-r12					MBSFN-AreaId-r12		OPTIONAL,	-- Need OR
	carrierFreq-r12						ARFCN-ValueEUTRA-r9,
	...
}

-- ASN1STOP

MasterInformationBlock ::=			[UNIVERSAL 16] IMPLICIT NULL {
	dl-Bandwidth						ENUMERATED {
											n6, n15, n25, n50, n75, n100},
	phich-Config						PHICH-Config,
	systemFrameNumber					BIT STRING (SIZE (8)),
	spare								BIT STRING (SIZE (10))
}


-- ASN1STOP

MBMSCountingRequest-r10 ::=		[UNIVERSAL 16] IMPLICIT NULL {
	countingRequestList-r10			CountingRequestList-r10,
	lateNonCriticalExtension		OCTET STRING						OPTIONAL,
	nonCriticalExtension			[UNIVERSAL 16] IMPLICIT NULL {}							OPTIONAL
}

CountingRequestList-r10 ::=	[UNIVERSAL 16] IMPLICIT NULL (SIZE (1..maxServiceCount)) OF CountingRequestInfo-r10

CountingRequestInfo-r10 ::=		[UNIVERSAL 16] IMPLICIT NULL {
	tmgi-r10							TMGI-r9,
	...
}

-- ASN1STOP

MBMSCountingResponse-r10 ::=			[UNIVERSAL 16] IMPLICIT NULL {
	criticalExtensions					CHOICE {
		c1									CHOICE {
			countingResponse-r10				MBMSCountingResponse-r10-IEs,
			spare3 NULL, spare2 NULL, spare1 NULL
		},
		criticalExtensionsFuture			[UNIVERSAL 16] IMPLICIT NULL {}
	}
}

MBMSCountingResponse-r10-IEs ::=	[UNIVERSAL 16] IMPLICIT NULL {
	mbsfn-AreaIndex-r10				INTEGER (0..maxMBSFN-Area-1) 						OPTIONAL,
	countingResponseList-r10		CountingResponseList-r10			OPTIONAL,
	lateNonCriticalExtension		OCTET STRING						OPTIONAL,
	nonCriticalExtension			[UNIVERSAL 16] IMPLICIT NULL {}							OPTIONAL
}

CountingResponseList-r10 ::=		[UNIVERSAL 16] IMPLICIT NULL (SIZE (1..maxServiceCount)) OF CountingResponseInfo-r10

CountingResponseInfo-r10 ::=		[UNIVERSAL 16] IMPLICIT NULL {
	countingResponseService-r10	INTEGER (0..maxServiceCount-1),
	...
}

-- ASN1STOP

MBMSInterestIndication-r11 ::=		[UNIVERSAL 16] IMPLICIT NULL {
	criticalExtensions					CHOICE {
		c1									CHOICE {
			interestIndication-r11				MBMSInterestIndication-r11-IEs,
			spare3 NULL, spare2 NULL, spare1 NULL
		},
		criticalExtensionsFuture			[UNIVERSAL 16] IMPLICIT NULL {}
	}
}

MBMSInterestIndication-r11-IEs ::=	[UNIVERSAL 16] IMPLICIT NULL {
	mbms-FreqList-r11					CarrierFreqListMBMS-r11			OPTIONAL,
	mbms-Priority-r11					ENUMERATED {true}				OPTIONAL,
	lateNonCriticalExtension			OCTET STRING					OPTIONAL,
	nonCriticalExtension				MBMSInterestIndication-r13-IEs	OPTIONAL
}

MBMSInterestIndication-r13-IEs ::=	[UNIVERSAL 16] IMPLICIT NULL {
	mbms-Services-r13					MBMSServiceList-r13				OPTIONAL,
	nonCriticalExtension				[UNIVERSAL 16] IMPLICIT NULL {}						OPTIONAL
}

-- ASN1STOP

MBSFNAreaConfiguration-r9 ::=		[UNIVERSAL 16] IMPLICIT NULL {
	commonSF-Alloc-r9					CommonSF-AllocPatternList-r9,
	commonSF-AllocPeriod-r9				ENUMERATED {
												rf4, rf8, rf16, rf32, rf64, rf128, rf256},
	pmch-InfoList-r9					PMCH-InfoList-r9,
	nonCriticalExtension				MBSFNAreaConfiguration-v930-IEs	OPTIONAL
}

MBSFNAreaConfiguration-v930-IEs ::= [UNIVERSAL 16] IMPLICIT NULL {
	lateNonCriticalExtension			OCTET STRING						OPTIONAL,
	nonCriticalExtension				MBSFNAreaConfiguration-v1250-IEs		OPTIONAL
}

MBSFNAreaConfiguration-v1250-IEs ::= [UNIVERSAL 16] IMPLICIT NULL {
	pmch-InfoListExt-r12				PMCH-InfoListExt-r12 				OPTIONAL, 	-- Need OR
	nonCriticalExtension				[UNIVERSAL 16] IMPLICIT NULL {}							OPTIONAL
}

CommonSF-AllocPatternList-r9 ::=	[UNIVERSAL 16] IMPLICIT NULL (SIZE (1..maxMBSFN-Allocations)) OF MBSFN-SubframeConfig

-- ASN1STOP

MeasurementReport ::=				[UNIVERSAL 16] IMPLICIT NULL {
	criticalExtensions					CHOICE {
		c1									CHOICE{
			measurementReport-r8				MeasurementReport-r8-IEs,
			spare7 NULL,
			spare6 NULL, spare5 NULL, spare4 NULL,
			spare3 NULL, spare2 NULL, spare1 NULL
		},
		criticalExtensionsFuture			[UNIVERSAL 16] IMPLICIT NULL {}
	}
}

MeasurementReport-r8-IEs ::=		[UNIVERSAL 16] IMPLICIT NULL {
	measResults							MeasResults,
	nonCriticalExtension				MeasurementReport-v8a0-IEs							OPTIONAL
}

MeasurementReport-v8a0-IEs ::= [UNIVERSAL 16] IMPLICIT NULL {
	lateNonCriticalExtension			OCTET STRING						OPTIONAL,
	nonCriticalExtension				[UNIVERSAL 16] IMPLICIT NULL {}							OPTIONAL
}

-- ASN1STOP

MobilityFromEUTRACommand ::=		[UNIVERSAL 16] IMPLICIT NULL {
	rrc-TransactionIdentifier			RRC-TransactionIdentifier,
	criticalExtensions					CHOICE {
		c1									CHOICE{
			mobilityFromEUTRACommand-r8		MobilityFromEUTRACommand-r8-IEs,
			mobilityFromEUTRACommand-r9 		MobilityFromEUTRACommand-r9-IEs,
			spare2 NULL, spare1 	NULL
		},
		criticalExtensionsFuture			[UNIVERSAL 16] IMPLICIT NULL {}
	}
}

MobilityFromEUTRACommand-r8-IEs ::=	[UNIVERSAL 16] IMPLICIT NULL {
	cs-FallbackIndicator				BOOLEAN,
	purpose								CHOICE{
		handover							Handover,
		cellChangeOrder						CellChangeOrder
	},
	nonCriticalExtension				MobilityFromEUTRACommand-v8a0-IEs	OPTIONAL
}

MobilityFromEUTRACommand-v8a0-IEs ::= [UNIVERSAL 16] IMPLICIT NULL {
	lateNonCriticalExtension			OCTET STRING						OPTIONAL,
	nonCriticalExtension				MobilityFromEUTRACommand-v8d0-IEs	OPTIONAL
}

MobilityFromEUTRACommand-v8d0-IEs ::= [UNIVERSAL 16] IMPLICIT NULL {
	bandIndicator						BandIndicatorGERAN			OPTIONAL,	-- Cond GERAN
	nonCriticalExtension				[UNIVERSAL 16] IMPLICIT NULL {}					OPTIONAL
}

MobilityFromEUTRACommand-r9-IEs ::=	[UNIVERSAL 16] IMPLICIT NULL {
	cs-FallbackIndicator				BOOLEAN,
	purpose								CHOICE{
		handover							Handover,
		cellChangeOrder						CellChangeOrder,
		e-CSFB-r9							E-CSFB-r9,
		...
	},
	nonCriticalExtension				MobilityFromEUTRACommand-v930-IEs	OPTIONAL
}

MobilityFromEUTRACommand-v930-IEs ::= [UNIVERSAL 16] IMPLICIT NULL {
	lateNonCriticalExtension			OCTET STRING						OPTIONAL,
	nonCriticalExtension				MobilityFromEUTRACommand-v960-IEs	OPTIONAL
}

MobilityFromEUTRACommand-v960-IEs ::= [UNIVERSAL 16] IMPLICIT NULL {
	bandIndicator						BandIndicatorGERAN			OPTIONAL,	-- Cond GERAN
	nonCriticalExtension				[UNIVERSAL 16] IMPLICIT NULL {}					OPTIONAL
}

Handover ::=						[UNIVERSAL 16] IMPLICIT NULL {
	targetRAT-Type						ENUMERATED {
											utra, geran, cdma2000-1XRTT, cdma2000-HRPD,
											spare4,	spare3, spare2, spare1, ...},
	targetRAT-MessageContainer			OCTET STRING,
	nas-SecurityParamFromEUTRA			OCTET STRING (SIZE (1)) 	OPTIONAL,	-- Cond UTRAGERAN
	systemInformation					SI-OrPSI-GERAN				OPTIONAL	-- Cond PSHO
}

CellChangeOrder ::=				[UNIVERSAL 16] IMPLICIT NULL {
	t304								ENUMERATED {
											ms100, ms200, ms500, ms1000,
											ms2000, ms4000, ms8000, spare1},
	targetRAT-Type						CHOICE {
			geran							[UNIVERSAL 16] IMPLICIT NULL {
				physCellId						PhysCellIdGERAN,
				carrierFreq						CarrierFreqGERAN,
				networkControlOrder				BIT STRING (SIZE (2)) 		OPTIONAL,	-- Need OP
				systemInformation				SI-OrPSI-GERAN				OPTIONAL	-- Need OP
			},
			...
	}
}

SI-OrPSI-GERAN ::=					CHOICE {
	si									SystemInfoListGERAN,
	psi									SystemInfoListGERAN
}

E-CSFB-r9 ::=						[UNIVERSAL 16] IMPLICIT NULL {
	messageContCDMA2000-1XRTT-r9		OCTET STRING		OPTIONAL, 	-- Need ON
	mobilityCDMA2000-HRPD-r9			ENUMERATED {
											handover, redirection 
										}					OPTIONAL,	-- Need OP
	messageContCDMA2000-HRPD-r9		OCTET STRING		OPTIONAL, 	-- Cond concHO
	redirectCarrierCDMA2000-HRPD-r9	CarrierFreqCDMA2000	OPTIONAL	-- Cond concRedir
}

-- ASN1STOP

Paging ::=					[UNIVERSAL 16] IMPLICIT NULL {
	pagingRecordList				PagingRecordList 					OPTIONAL,	-- Need ON
	systemInfoModification			ENUMERATED {true}					OPTIONAL,	-- Need ON
	etws-Indication					ENUMERATED {true}					OPTIONAL,	-- Need ON
	nonCriticalExtension			Paging-v890-IEs						OPTIONAL
}

Paging-v890-IEs ::=			[UNIVERSAL 16] IMPLICIT NULL {
	lateNonCriticalExtension		OCTET STRING							OPTIONAL,
	nonCriticalExtension			Paging-v920-IEs							OPTIONAL
}

Paging-v920-IEs ::=			[UNIVERSAL 16] IMPLICIT NULL {
	cmas-Indication-r9				ENUMERATED {true}					OPTIONAL,	-- Need ON
	nonCriticalExtension				Paging-v1130-IEs				OPTIONAL
}

Paging-v1130-IEs ::=			[UNIVERSAL 16] IMPLICIT NULL {
	eab-ParamModification-r11		ENUMERATED {true}					OPTIONAL,	-- Need ON
	nonCriticalExtension			Paging-v13xx-IEs					OPTIONAL
}

Paging-v13xx-IEs ::=			[UNIVERSAL 16] IMPLICIT NULL {
	redistributionIndication-r13	ENUMERATED {true}					OPTIONAL,	--Need ON
	systemInfoModification-eDRX-r13	ENUMERATED {true}					OPTIONAL,	-- Need ON
	nonCriticalExtension			[UNIVERSAL 16] IMPLICIT NULL {}							OPTIONAL
}

PagingRecordList ::=				[UNIVERSAL 16] IMPLICIT NULL (SIZE (1..maxPageRec)) OF PagingRecord

PagingRecord ::=					[UNIVERSAL 16] IMPLICIT NULL {
	ue-Identity							PagingUE-Identity,
	cn-Domain							ENUMERATED	{ps, cs},
	...
}

PagingUE-Identity ::=				CHOICE {
	s-TMSI								S-TMSI,
	imsi								IMSI,
	...
}

IMSI ::=							[UNIVERSAL 16] IMPLICIT NULL (SIZE (6..21)) OF IMSI-Digit

IMSI-Digit ::=						INTEGER (0..9)

-- ASN1STOP

ProximityIndication-r9 ::= [UNIVERSAL 16] IMPLICIT NULL {
	criticalExtensions					CHOICE {
		c1									CHOICE {
			proximityIndication-r9				ProximityIndication-r9-IEs,
			spare3 NULL, spare2 NULL, spare1 NULL
			},
		criticalExtensionsFuture			[UNIVERSAL 16] IMPLICIT NULL {}
	}
}

ProximityIndication-r9-IEs ::= [UNIVERSAL 16] IMPLICIT NULL {
	type-r9								ENUMERATED {entering, leaving},
	carrierFreq-r9						CHOICE {
		eutra-r9							ARFCN-ValueEUTRA,
		utra-r9								ARFCN-ValueUTRA,
	--	...,
		eutra2-v9e0							ARFCN-ValueEUTRA-v9e0
	},
	nonCriticalExtension				ProximityIndication-v930-IEs							OPTIONAL
}

ProximityIndication-v930-IEs ::= [UNIVERSAL 16] IMPLICIT NULL {
	lateNonCriticalExtension			OCTET STRING						OPTIONAL,
	nonCriticalExtension				[UNIVERSAL 16] IMPLICIT NULL {}							OPTIONAL
}

-- ASN1STOP

RNReconfiguration-r10 ::=		[UNIVERSAL 16] IMPLICIT NULL {
	rrc-TransactionIdentifier		RRC-TransactionIdentifier,
	criticalExtensions				CHOICE {
		c1								CHOICE {
			rnReconfiguration-r10		RNReconfiguration-r10-IEs, 
			spare3 NULL, spare2 NULL, spare1 NULL
		},
		criticalExtensionsFuture		[UNIVERSAL 16] IMPLICIT NULL {}
	}
}

RNReconfiguration-r10-IEs ::=		[UNIVERSAL 16] IMPLICIT NULL {
	rn-SystemInfo-r10					RN-SystemInfo-r10			OPTIONAL,	-- Need ON
	rn-SubframeConfig-r10				RN-SubframeConfig-r10			OPTIONAL,	-- Need ON
	lateNonCriticalExtension			OCTET STRING					OPTIONAL,
	nonCriticalExtension				[UNIVERSAL 16] IMPLICIT NULL {}						OPTIONAL
}

RN-SystemInfo-r10 ::=			[UNIVERSAL 16] IMPLICIT NULL {
	systemInformationBlockType1-r10		OCTET STRING (CONTAINING SystemInformationBlockType1)	OPTIONAL,	-- Need ON
	systemInformationBlockType2-r10		SystemInformationBlockType2		OPTIONAL,	-- Need ON
	...
}

-- ASN1STOP

RNReconfigurationComplete-r10 ::=		[UNIVERSAL 16] IMPLICIT NULL {
	rrc-TransactionIdentifier				RRC-TransactionIdentifier,
	criticalExtensions						CHOICE {
		c1										CHOICE{
			rnReconfigurationComplete-r10			RNReconfigurationComplete-r10-IEs,
			spare3 NULL, spare2 NULL, spare1 NULL
		},
		criticalExtensionsFuture				[UNIVERSAL 16] IMPLICIT NULL {}
	}
}

RNReconfigurationComplete-r10-IEs ::=	[UNIVERSAL 16] IMPLICIT NULL {
	lateNonCriticalExtension				OCTET STRING				OPTIONAL,
	nonCriticalExtension					[UNIVERSAL 16] IMPLICIT NULL {}					OPTIONAL
}

-- ASN1STOP

RRCConnectionReconfiguration ::=	[UNIVERSAL 16] IMPLICIT NULL {
	rrc-TransactionIdentifier			RRC-TransactionIdentifier,
	criticalExtensions					CHOICE {
		c1									CHOICE{
			rrcConnectionReconfiguration-r8		RRCConnectionReconfiguration-r8-IEs,
			spare7 NULL,
			spare6 NULL, spare5 NULL, spare4 NULL,
			spare3 NULL, spare2 NULL, spare1 NULL
		},
		criticalExtensionsFuture			[UNIVERSAL 16] IMPLICIT NULL {}
	}
}

RRCConnectionReconfiguration-r8-IEs ::= [UNIVERSAL 16] IMPLICIT NULL {
	measConfig							MeasConfig						OPTIONAL,	-- Need ON
	mobilityControlInfo					MobilityControlInfo				OPTIONAL,	-- Cond HO
	dedicatedInfoNASList				[UNIVERSAL 16] IMPLICIT NULL (SIZE(1..maxDRB)) OF
											DedicatedInfoNAS			OPTIONAL,	-- Cond nonHO
	radioResourceConfigDedicated		RadioResourceConfigDedicated	OPTIONAL, -- Cond HO-toEUTRA
	securityConfigHO					SecurityConfigHO				OPTIONAL,	-- Cond HO
	nonCriticalExtension				RRCConnectionReconfiguration-v890-IEs	OPTIONAL
}

RRCConnectionReconfiguration-v890-IEs ::= [UNIVERSAL 16] IMPLICIT NULL {
	lateNonCriticalExtension			OCTET STRING (CONTAINING RRCConnectionReconfiguration-v8m0-IEs)	OPTIONAL,
	nonCriticalExtension				RRCConnectionReconfiguration-v920-IEs	OPTIONAL
}

-- Late non-critical extensions:
RRCConnectionReconfiguration-v8m0-IEs ::= [UNIVERSAL 16] IMPLICIT NULL {
	-- Following field is only for pre REL-10 late non-critical extensions
	lateNonCriticalExtension			OCTET STRING					OPTIONAL, 
	nonCriticalExtension				RRCConnectionReconfiguration-v10i0-IEs		OPTIONAL
}

RRCConnectionReconfiguration-v10i0-IEs ::= [UNIVERSAL 16] IMPLICIT NULL {
	antennaInfoDedicatedPCell-v10i0		AntennaInfoDedicated-v10i0			OPTIONAL,	-- Need ON
	-- Following field is only for late non-critical extensions from REL-10
	nonCriticalExtension				[UNIVERSAL 16] IMPLICIT NULL {}				OPTIONAL
}

-- Regular non-critical extensions:
RRCConnectionReconfiguration-v920-IEs ::= [UNIVERSAL 16] IMPLICIT NULL {
	otherConfig-r9						OtherConfig-r9					OPTIONAL,	-- Need ON
	fullConfig-r9						ENUMERATED {true}				OPTIONAL,	-- Cond HO-Reestab
	nonCriticalExtension				RRCConnectionReconfiguration-v1020-IEs	OPTIONAL
}

RRCConnectionReconfiguration-v1020-IEs ::= [UNIVERSAL 16] IMPLICIT NULL {
	sCellToReleaseList-r10				SCellToReleaseList-r10			OPTIONAL,	-- Need ON
	sCellToAddModList-r10				SCellToAddModList-r10			OPTIONAL,	-- Need ON
	nonCriticalExtension				RRCConnectionReconfiguration-v1130-IEs	OPTIONAL
}

RRCConnectionReconfiguration-v1130-IEs ::= [UNIVERSAL 16] IMPLICIT NULL {
	systemInfomationBlockType1Dedicated-r11	OCTET STRING (CONTAINING SystemInformationBlockType1)																			OPTIONAL,	-- Need ON
	nonCriticalExtension				RRCConnectionReconfiguration-v1250-IEs	OPTIONAL
}

RRCConnectionReconfiguration-v1250-IEs ::= [UNIVERSAL 16] IMPLICIT NULL {
	wlan-OffloadInfo-r12				CHOICE {
		release 								NULL,
		setup									[UNIVERSAL 16] IMPLICIT NULL {
			wlan-OffloadConfigDedicated-r12		WLAN-OffloadConfig-r12,
			t350-r12								ENUMERATED {min5, min10, min20, min30, min60,
												 min120, min180, spare1}	OPTIONAL	-- Need OR
		}
	}																	OPTIONAL,		-- Need ON
	scg-Configuration-r12				SCG-Configuration-r12		OPTIONAL, 	-- Cond nonFullConfig
	sl-SyncTxControl-r12				SL-SyncTxControl-r12			OPTIONAL,	-- Need ON
	sl-DiscConfig-r12					SL-DiscConfig-r12				OPTIONAL,	-- Need ON
	sl-CommConfig-r12					SL-CommConfig-r12				OPTIONAL,	-- Need ON
	nonCriticalExtension				RRCConnectionReconfiguration-v13xy-IEs	OPTIONAL
}

RRCConnectionReconfiguration-v13xy-IEs ::= [UNIVERSAL 16] IMPLICIT NULL {
	sCellToReleaseListExt-r13			SCellToReleaseListExt-r13		OPTIONAL,	-- Need ON
	sCellToAddModListExt-r13			SCellToAddModListExt-r13		OPTIONAL,	-- Need ON
	nonCriticalExtension				[UNIVERSAL 16] IMPLICIT NULL {}						OPTIONAL
}

SL-SyncTxControl-r12 ::=			[UNIVERSAL 16] IMPLICIT NULL {
	networkControlledSyncTx-r12				ENUMERATED {on, off}		OPTIONAL		-- Need OP
}

PSCellToAddMod-r12 ::=				[UNIVERSAL 16] IMPLICIT NULL {
	sCellIndex-r12						SCellIndex-r10,
	cellIdentification-r12				[UNIVERSAL 16] IMPLICIT NULL {
		physCellId-r12						PhysCellId,
		dl-CarrierFreq-r12					ARFCN-ValueEUTRA-r9
	}																	OPTIONAL,	-- Cond SCellAdd
	radioResourceConfigCommonPSCell-r12		RadioResourceConfigCommonPSCell-r12	OPTIONAL,	-- Cond SCellAdd
	radioResourceConfigDedicatedPSCell-r12	RadioResourceConfigDedicatedPSCell-r12	OPTIONAL, -- Cond SCellAdd2
----	...,
--	[[	
        antennaInfoDedicatedPSCell-v1280		AntennaInfoDedicated-v10i0	OPTIONAL, -- Need ON
--	]],
--	[[	
        sCellIndex-r13					SCellIndex-r13	OPTIONAL		-- Need ON
--	]]
}

PowerCoordinationInfo-r12 ::= [UNIVERSAL 16] IMPLICIT NULL {
	p-MeNB-r12							INTEGER (1..16),
	p-SeNB-r12							INTEGER (1..16),
	powerControlMode-r12				INTEGER (1..2)
}

SCellToAddModList-r10 ::=		[UNIVERSAL 16] IMPLICIT NULL (SIZE (1..maxSCell-r10)) OF SCellToAddMod-r10

SCellToAddModListExt-r13 ::=	[UNIVERSAL 16] IMPLICIT NULL (SIZE (maxSCell-Plus1..maxSCell-r13)) OF SCellToAddMod-r13

SCellToAddMod-r10 ::=			[UNIVERSAL 16] IMPLICIT NULL {
	sCellIndex-r10						SCellIndex-r10,
	cellIdentification-r10				[UNIVERSAL 16] IMPLICIT NULL {
		physCellId-r10						PhysCellId,
		dl-CarrierFreq-r10					ARFCN-ValueEUTRA
	}																OPTIONAL,	-- Cond SCellAdd
	radioResourceConfigCommonSCell-r10		RadioResourceConfigCommonSCell-r10	OPTIONAL,	-- Cond SCellAdd
	radioResourceConfigDedicatedSCell-r10	RadioResourceConfigDedicatedSCell-r10	OPTIONAL--,	
	-- Cond SCellAdd2
--	...,
--	[[	dl-CarrierFreq-v1090				ARFCN-ValueEUTRA-v9e0	OPTIONAL	
-- Cond EARFCN-max
--	]],
--	[[	antennaInfoDedicatedSCell-v10i0		AntennaInfoDedicated-v10i0	OPTIONAL	
-- Need ON
--	]]
}

SCellToAddMod-r13 ::=			[UNIVERSAL 16] IMPLICIT NULL {
	sCellIndex-v13xy						SCellIndex-v13xy,
	cellIdentification-r13				[UNIVERSAL 16] IMPLICIT NULL {
		physCellId-r13						PhysCellId,
		dl-CarrierFreq-r13					ARFCN-ValueEUTRA-r9
	}																OPTIONAL,	-- Cond SCellAdd
	radioResourceConfigCommonSCell-r13		RadioResourceConfigCommonSCell-r10	OPTIONAL,	-- Cond SCellAdd
	radioResourceConfigDedicatedSCell-r13	RadioResourceConfigDedicatedSCell-r10	OPTIONAL	-- Cond SCellAdd2
}

SCellToReleaseList-r10 ::=			[UNIVERSAL 16] IMPLICIT NULL (SIZE (1..maxSCell-r10)) OF SCellIndex-r10

SCellToReleaseListExt-r13 ::=			[UNIVERSAL 16] IMPLICIT NULL (SIZE (maxSCell-Plus1..maxSCell-r13)) OF SCellIndex-v13xy

SCG-Configuration-r12 ::=			CHOICE {
	release								NULL,
	setup								[UNIVERSAL 16] IMPLICIT NULL {
		scg-ConfigPartMCG-r12				[UNIVERSAL 16] IMPLICIT NULL {
			scg-Counter-r12						INTEGER (0.. 65535)			OPTIONAL,	-- Need ON
			powerCoordinationInfo-r12			PowerCoordinationInfo-r12	OPTIONAL,	-- Need ON
			...
		}																OPTIONAL,	-- Need ON
		scg-ConfigPartSCG-r12				SCG-ConfigPartSCG-r12 		OPTIONAL	-- Need ON
	}
}

SCG-ConfigPartSCG-r12 ::=			[UNIVERSAL 16] IMPLICIT NULL {
	radioResourceConfigDedicatedSCG-r12	RadioResourceConfigDedicatedSCG-r12	OPTIONAL,	-- Need ON
	sCellToReleaseListSCG-r12			SCellToReleaseList-r10		OPTIONAL,	-- Need ON
	pSCellToAddMod-r12					PSCellToAddMod-r12			OPTIONAL,	-- Need ON
	sCellToAddModListSCG-r12			SCellToAddModList-r10		OPTIONAL,	-- Need ON
	mobilityControlInfoSCG-r12			MobilityControlInfoSCG-r12	OPTIONAL --,
	-- Need ON
--	...,
--	[[
--	sCellToReleaseListSCG-Ext-r13			SCellToReleaseListExt-r13		OPTIONAL,	
-- Need ON
--	sCellToAddModListSCG-Ext-r13				SCellToAddModListExt-r13	OPTIONAL	
-- Need ON
--	]]
}

SecurityConfigHO ::=				[UNIVERSAL 16] IMPLICIT NULL {
	handoverType						CHOICE {
		intraLTE							[UNIVERSAL 16] IMPLICIT NULL {
			securityAlgorithmConfig				SecurityAlgorithmConfig		OPTIONAL,	-- Cond fullConfig
			keyChangeIndicator					BOOLEAN,
			nextHopChainingCount				NextHopChainingCount
		},
		interRAT							[UNIVERSAL 16] IMPLICIT NULL {
			securityAlgorithmConfig				SecurityAlgorithmConfig,
			nas-SecurityParamToEUTRA			OCTET STRING (SIZE(6))
		}
	},
	...
}


-- ASN1STOP

RRCConnectionReconfigurationComplete ::= [UNIVERSAL 16] IMPLICIT NULL {
	rrc-TransactionIdentifier			RRC-TransactionIdentifier,
	criticalExtensions					CHOICE {
		rrcConnectionReconfigurationComplete-r8
											RRCConnectionReconfigurationComplete-r8-IEs,
		criticalExtensionsFuture			[UNIVERSAL 16] IMPLICIT NULL {}
	}
}

RRCConnectionReconfigurationComplete-r8-IEs ::= [UNIVERSAL 16] IMPLICIT NULL {
	nonCriticalExtension				RRCConnectionReconfigurationComplete-v8a0-IEs	OPTIONAL
}

RRCConnectionReconfigurationComplete-v8a0-IEs ::= [UNIVERSAL 16] IMPLICIT NULL {
	lateNonCriticalExtension			OCTET STRING						OPTIONAL,
	nonCriticalExtension				RRCConnectionReconfigurationComplete-v1020-IEs	OPTIONAL
}

RRCConnectionReconfigurationComplete-v1020-IEs ::= [UNIVERSAL 16] IMPLICIT NULL {
	rlf-InfoAvailable-r10				ENUMERATED {true}				OPTIONAL,
	logMeasAvailable-r10				ENUMERATED {true}				OPTIONAL,
	nonCriticalExtension				RRCConnectionReconfigurationComplete-v1130-IEs	OPTIONAL
}

RRCConnectionReconfigurationComplete-v1130-IEs ::= [UNIVERSAL 16] IMPLICIT NULL {
	connEstFailInfoAvailable-r11		ENUMERATED {true}				OPTIONAL,
	nonCriticalExtension				RRCConnectionReconfigurationComplete-v1250-IEs	OPTIONAL
}

RRCConnectionReconfigurationComplete-v1250-IEs ::= [UNIVERSAL 16] IMPLICIT NULL {
	logMeasAvailableMBSFN-r12			ENUMERATED {true}				OPTIONAL,
	nonCriticalExtension				[UNIVERSAL 16] IMPLICIT NULL {}						OPTIONAL
}

-- ASN1STOP

RRCConnectionReestablishment ::=	[UNIVERSAL 16] IMPLICIT NULL {
	rrc-TransactionIdentifier			RRC-TransactionIdentifier,
	criticalExtensions					CHOICE {
		c1									CHOICE{
			rrcConnectionReestablishment-r8		RRCConnectionReestablishment-r8-IEs,
			spare7 NULL,
			spare6 NULL, spare5 NULL, spare4 	NULL,
			spare3 NULL, spare2 NULL, spare1 	NULL
		},
		criticalExtensionsFuture			[UNIVERSAL 16] IMPLICIT NULL {}
	}
}

RRCConnectionReestablishment-r8-IEs ::= [UNIVERSAL 16] IMPLICIT NULL {
	radioResourceConfigDedicated		RadioResourceConfigDedicated,
	nextHopChainingCount				NextHopChainingCount,
	nonCriticalExtension				RRCConnectionReestablishment-v8a0-IEs	OPTIONAL
}

RRCConnectionReestablishment-v8a0-IEs ::= [UNIVERSAL 16] IMPLICIT NULL {
	lateNonCriticalExtension			OCTET STRING						OPTIONAL,
	nonCriticalExtension				[UNIVERSAL 16] IMPLICIT NULL {}							OPTIONAL
}

-- ASN1STOP

RRCConnectionReestablishmentComplete ::= [UNIVERSAL 16] IMPLICIT NULL {
	rrc-TransactionIdentifier			RRC-TransactionIdentifier,
	criticalExtensions					CHOICE {
		rrcConnectionReestablishmentComplete-r8
											RRCConnectionReestablishmentComplete-r8-IEs,
		criticalExtensionsFuture			[UNIVERSAL 16] IMPLICIT NULL {}
	}
}

RRCConnectionReestablishmentComplete-r8-IEs ::= [UNIVERSAL 16] IMPLICIT NULL {
	nonCriticalExtension				RRCConnectionReestablishmentComplete-v920-IEs	OPTIONAL
}

RRCConnectionReestablishmentComplete-v920-IEs ::= [UNIVERSAL 16] IMPLICIT NULL {
	rlf-InfoAvailable-r9				ENUMERATED {true}				OPTIONAL,
	nonCriticalExtension				RRCConnectionReestablishmentComplete-v8a0-IEs	OPTIONAL
}

RRCConnectionReestablishmentComplete-v8a0-IEs ::= [UNIVERSAL 16] IMPLICIT NULL {
	lateNonCriticalExtension			OCTET STRING						OPTIONAL,
	nonCriticalExtension				RRCConnectionReestablishmentComplete-v1020-IEs	OPTIONAL
}

RRCConnectionReestablishmentComplete-v1020-IEs ::= [UNIVERSAL 16] IMPLICIT NULL {
	logMeasAvailable-r10				ENUMERATED {true}				OPTIONAL,
	nonCriticalExtension				RRCConnectionReestablishmentComplete-v1130-IEs	OPTIONAL
}

RRCConnectionReestablishmentComplete-v1130-IEs ::= [UNIVERSAL 16] IMPLICIT NULL {
	connEstFailInfoAvailable-r11		ENUMERATED {true}				OPTIONAL,
	nonCriticalExtension				RRCConnectionReestablishmentComplete-v1250-IEs	OPTIONAL
}

RRCConnectionReestablishmentComplete-v1250-IEs ::= [UNIVERSAL 16] IMPLICIT NULL {
	logMeasAvailableMBSFN-r12			ENUMERATED {true}				OPTIONAL,
	nonCriticalExtension				[UNIVERSAL 16] IMPLICIT NULL {}						OPTIONAL
}

-- ASN1STOP

RRCConnectionReestablishmentReject ::= [UNIVERSAL 16] IMPLICIT NULL {
	criticalExtensions					CHOICE {
		rrcConnectionReestablishmentReject-r8
											RRCConnectionReestablishmentReject-r8-IEs,
		criticalExtensionsFuture			[UNIVERSAL 16] IMPLICIT NULL {}
	}
}

RRCConnectionReestablishmentReject-r8-IEs ::= [UNIVERSAL 16] IMPLICIT NULL {
	nonCriticalExtension				RRCConnectionReestablishmentReject-v8a0-IEs	OPTIONAL
}

RRCConnectionReestablishmentReject-v8a0-IEs ::= [UNIVERSAL 16] IMPLICIT NULL {
	lateNonCriticalExtension			OCTET STRING						OPTIONAL,
	nonCriticalExtension				[UNIVERSAL 16] IMPLICIT NULL {}							OPTIONAL
}

-- ASN1STOP

RRCConnectionReestablishmentRequest ::= [UNIVERSAL 16] IMPLICIT NULL {
	criticalExtensions					CHOICE {
		rrcConnectionReestablishmentRequest-r8
											RRCConnectionReestablishmentRequest-r8-IEs,
		criticalExtensionsFuture			[UNIVERSAL 16] IMPLICIT NULL {}
	}
}

RRCConnectionReestablishmentRequest-r8-IEs ::= [UNIVERSAL 16] IMPLICIT NULL {
	ue-Identity							ReestabUE-Identity,
	reestablishmentCause				ReestablishmentCause,
	spare								BIT STRING (SIZE (2))
}

ReestabUE-Identity ::=				[UNIVERSAL 16] IMPLICIT NULL {
	c-RNTI								C-RNTI,
	physCellId							PhysCellId,
	shortMAC-I							ShortMAC-I
}

ReestablishmentCause ::=			ENUMERATED {
										reconfigurationFailure, handoverFailure,
										otherFailure, spare1}

-- ASN1STOP

RRCConnectionReject ::=				[UNIVERSAL 16] IMPLICIT NULL {
	criticalExtensions					CHOICE {
		c1									CHOICE {
			rrcConnectionReject-r8				RRCConnectionReject-r8-IEs,
			spare3 NULL, spare2 NULL, spare1 NULL
		},
		criticalExtensionsFuture			[UNIVERSAL 16] IMPLICIT NULL {}
	}
}

RRCConnectionReject-r8-IEs ::=		[UNIVERSAL 16] IMPLICIT NULL {
	waitTime							INTEGER (1..16),
	nonCriticalExtension				RRCConnectionReject-v8a0-IEs		OPTIONAL
}

RRCConnectionReject-v8a0-IEs ::= [UNIVERSAL 16] IMPLICIT NULL {
	lateNonCriticalExtension			OCTET STRING						OPTIONAL,
	nonCriticalExtension				RRCConnectionReject-v1020-IEs		OPTIONAL
}

RRCConnectionReject-v1020-IEs ::=	[UNIVERSAL 16] IMPLICIT NULL {
	extendedWaitTime-r10				INTEGER (1..1800)					OPTIONAL,	-- Need ON
	nonCriticalExtension				RRCConnectionReject-v1130-IEs		OPTIONAL
}

RRCConnectionReject-v1130-IEs ::=	[UNIVERSAL 16] IMPLICIT NULL {
	deprioritisationReq-r11				[UNIVERSAL 16] IMPLICIT NULL {
		deprioritisationType-r11			ENUMERATED {frequency, e-utra},
		deprioritisationTimer-r11			ENUMERATED {min5, min10, min15, min30}
	}																		OPTIONAL,	-- Need ON
	nonCriticalExtension				[UNIVERSAL 16] IMPLICIT NULL {}							OPTIONAL
}

-- ASN1STOP

RRCConnectionRelease ::=			[UNIVERSAL 16] IMPLICIT NULL {
	rrc-TransactionIdentifier			RRC-TransactionIdentifier,
	criticalExtensions					CHOICE {
		c1									CHOICE {
			rrcConnectionRelease-r8				RRCConnectionRelease-r8-IEs,
			spare3 NULL, spare2 NULL, spare1 NULL
		},
		criticalExtensionsFuture			[UNIVERSAL 16] IMPLICIT NULL {}
	}
}

RRCConnectionRelease-r8-IEs ::=		[UNIVERSAL 16] IMPLICIT NULL {
	releaseCause						ReleaseCause,
	redirectedCarrierInfo				RedirectedCarrierInfo				OPTIONAL,	-- Need ON
	idleModeMobilityControlInfo			IdleModeMobilityControlInfo			OPTIONAL,	-- Need OP
	nonCriticalExtension				RRCConnectionRelease-v890-IEs		OPTIONAL
}

RRCConnectionRelease-v890-IEs ::=	[UNIVERSAL 16] IMPLICIT NULL {
	lateNonCriticalExtension			OCTET STRING (CONTAINING RRCConnectionRelease-v9e0-IEs)	OPTIONAL,
	nonCriticalExtension				RRCConnectionRelease-v920-IEs		OPTIONAL
}

-- Late non critical extensions
RRCConnectionRelease-v9e0-IEs ::= [UNIVERSAL 16] IMPLICIT NULL {
	redirectedCarrierInfo-v9e0			RedirectedCarrierInfo-v9e0			OPTIONAL,	-- Cond NoRedirect-r8
	idleModeMobilityControlInfo-v9e0	IdleModeMobilityControlInfo-v9e0	OPTIONAL,	-- Cond IdleInfoEUTRA
	nonCriticalExtension				[UNIVERSAL 16] IMPLICIT NULL {}							OPTIONAL
}

-- Regular non critical extensions
RRCConnectionRelease-v920-IEs ::=	[UNIVERSAL 16] IMPLICIT NULL {
	cellInfoList-r9					CHOICE {
		geran-r9						CellInfoListGERAN-r9,
		utra-FDD-r9						CellInfoListUTRA-FDD-r9,
		utra-TDD-r9						CellInfoListUTRA-TDD-r9,
	--	...,
		utra-TDD-r10					CellInfoListUTRA-TDD-r10
	}															OPTIONAL,	-- Cond Redirection
	nonCriticalExtension			RRCConnectionRelease-v1020-IEs		OPTIONAL
}

RRCConnectionRelease-v1020-IEs ::=	[UNIVERSAL 16] IMPLICIT NULL {
	extendedWaitTime-r10				INTEGER (1..1800)		OPTIONAL,	-- Need ON
	nonCriticalExtension			[UNIVERSAL 16] IMPLICIT NULL {}				OPTIONAL
}

ReleaseCause ::=				ENUMERATED {loadBalancingTAUrequired,
											other, cs-FallbackHighPriority-v1020, spare1}

RedirectedCarrierInfo ::=			CHOICE {
	eutra								ARFCN-ValueEUTRA,
	geran								CarrierFreqsGERAN,
	utra-FDD							ARFCN-ValueUTRA,
	utra-TDD							ARFCN-ValueUTRA,
	cdma2000-HRPD						CarrierFreqCDMA2000,
	cdma2000-1xRTT						CarrierFreqCDMA2000,
--	...,
	utra-TDD-r10						CarrierFreqListUTRA-TDD-r10
}

RedirectedCarrierInfo-v9e0 ::=			[UNIVERSAL 16] IMPLICIT NULL {
	eutra-v9e0								ARFCN-ValueEUTRA-v9e0
}

CarrierFreqListUTRA-TDD-r10 ::=			[UNIVERSAL 16] IMPLICIT NULL (SIZE (1..maxFreqUTRA-TDD-r10)) OF ARFCN-ValueUTRA

IdleModeMobilityControlInfo ::=		[UNIVERSAL 16] IMPLICIT NULL {
	freqPriorityListEUTRA				FreqPriorityListEUTRA			OPTIONAL,		-- Need ON
	freqPriorityListGERAN				FreqsPriorityListGERAN			OPTIONAL,		-- Need ON
	freqPriorityListUTRA-FDD			FreqPriorityListUTRA-FDD		OPTIONAL,		-- Need ON
	freqPriorityListUTRA-TDD			FreqPriorityListUTRA-TDD		OPTIONAL,		-- Need ON
	bandClassPriorityListHRPD			BandClassPriorityListHRPD		OPTIONAL,		-- Need ON
	bandClassPriorityList1XRTT			BandClassPriorityList1XRTT		OPTIONAL,		-- Need ON
	t320								ENUMERATED {
											min5, min10, min20, min30, min60, min120, min180,
											spare1}						OPTIONAL--,		
											-- Need OR
--	...,
--	[[	freqPriorityListExtEUTRA-r12		FreqPriorityListExtEUTRA-r12		OPTIONAL		
-- Need ON
--	]],
--	[[	freqPriorityListEUTRA-v13xy			FreqPriorityListEUTRA-v13xy			OPTIONAL,		
-- Need ON
--		freqPriorityListExtEUTRA-v13xy		FreqPriorityListExtEUTRA-v13xy		OPTIONAL		
-- Need ON
--	]]
}

IdleModeMobilityControlInfo-v9e0 ::=	[UNIVERSAL 16] IMPLICIT NULL {
	freqPriorityListEUTRA-v9e0			[UNIVERSAL 16] IMPLICIT NULL (SIZE (1..maxFreq)) OF FreqPriorityEUTRA-v9e0
}

FreqPriorityListEUTRA ::=			[UNIVERSAL 16] IMPLICIT NULL (SIZE (1..maxFreq)) OF FreqPriorityEUTRA

FreqPriorityListExtEUTRA-r12 ::=		[UNIVERSAL 16] IMPLICIT NULL (SIZE (1..maxFreq)) OF FreqPriorityEUTRA-r12

FreqPriorityListEUTRA-v13xy ::=			[UNIVERSAL 16] IMPLICIT NULL (SIZE (1..maxFreq)) OF FreqPriorityEUTRA-v13xy

FreqPriorityListExtEUTRA-v13xy ::=		[UNIVERSAL 16] IMPLICIT NULL (SIZE (1..maxFreq)) OF FreqPriorityEUTRA-v13xy

FreqPriorityEUTRA ::=				[UNIVERSAL 16] IMPLICIT NULL {
	carrierFreq							ARFCN-ValueEUTRA,
	cellReselectionPriority				CellReselectionPriority
}

FreqPriorityEUTRA-v9e0 ::=			[UNIVERSAL 16] IMPLICIT NULL {
	carrierFreq-v9e0					ARFCN-ValueEUTRA-v9e0		OPTIONAL	-- Cond EARFCN-max
}

FreqPriorityEUTRA-r12 ::=				[UNIVERSAL 16] IMPLICIT NULL {
	carrierFreq-r12							ARFCN-ValueEUTRA-r9,
	cellReselectionPriority-r12				CellReselectionPriority
}

FreqPriorityEUTRA-v13xy ::=				[UNIVERSAL 16] IMPLICIT NULL {
	cellReselectionSubPriority-r13				CellReselectionSubPriority-r13 		OPTIONAL		-- Need ON
}

FreqsPriorityListGERAN ::=			[UNIVERSAL 16] IMPLICIT NULL (SIZE (1..maxGNFG)) OF FreqsPriorityGERAN

FreqsPriorityGERAN ::=				[UNIVERSAL 16] IMPLICIT NULL {
	carrierFreqs						CarrierFreqsGERAN,
	cellReselectionPriority				CellReselectionPriority
}

FreqPriorityListUTRA-FDD ::=		[UNIVERSAL 16] IMPLICIT NULL (SIZE (1..maxUTRA-FDD-Carrier)) OF FreqPriorityUTRA-FDD

FreqPriorityUTRA-FDD ::=			[UNIVERSAL 16] IMPLICIT NULL {
	carrierFreq							ARFCN-ValueUTRA,
	cellReselectionPriority				CellReselectionPriority
}

FreqPriorityListUTRA-TDD ::=		[UNIVERSAL 16] IMPLICIT NULL (SIZE (1..maxUTRA-TDD-Carrier)) OF FreqPriorityUTRA-TDD

FreqPriorityUTRA-TDD ::=			[UNIVERSAL 16] IMPLICIT NULL {
	carrierFreq							ARFCN-ValueUTRA,
	cellReselectionPriority				CellReselectionPriority
}

BandClassPriorityListHRPD ::=		[UNIVERSAL 16] IMPLICIT NULL (SIZE (1..maxCDMA-BandClass)) OF BandClassPriorityHRPD

BandClassPriorityHRPD ::=			[UNIVERSAL 16] IMPLICIT NULL {
	bandClass							BandclassCDMA2000,
	cellReselectionPriority				CellReselectionPriority
}

BandClassPriorityList1XRTT ::=	[UNIVERSAL 16] IMPLICIT NULL (SIZE (1..maxCDMA-BandClass)) OF BandClassPriority1XRTT

BandClassPriority1XRTT ::=			[UNIVERSAL 16] IMPLICIT NULL {
	bandClass							BandclassCDMA2000,
	cellReselectionPriority				CellReselectionPriority
}

CellInfoListGERAN-r9 ::=		[UNIVERSAL 16] IMPLICIT NULL (SIZE (1..maxCellInfoGERAN-r9)) OF CellInfoGERAN-r9

CellInfoGERAN-r9 ::=				[UNIVERSAL 16] IMPLICIT NULL {
	physCellId-r9						PhysCellIdGERAN,
	carrierFreq-r9						CarrierFreqGERAN,
	systemInformation-r9				SystemInfoListGERAN
}

CellInfoListUTRA-FDD-r9 ::=			[UNIVERSAL 16] IMPLICIT NULL (SIZE (1..maxCellInfoUTRA-r9)) OF CellInfoUTRA-FDD-r9

CellInfoUTRA-FDD-r9 ::=				[UNIVERSAL 16] IMPLICIT NULL {
	physCellId-r9						PhysCellIdUTRA-FDD,
	utra-BCCH-Container-r9				OCTET STRING
}

CellInfoListUTRA-TDD-r9 ::=			[UNIVERSAL 16] IMPLICIT NULL (SIZE (1..maxCellInfoUTRA-r9)) OF CellInfoUTRA-TDD-r9

CellInfoUTRA-TDD-r9 ::=				[UNIVERSAL 16] IMPLICIT NULL {
	physCellId-r9						PhysCellIdUTRA-TDD,
	utra-BCCH-Container-r9				OCTET STRING
}

CellInfoListUTRA-TDD-r10 ::=		[UNIVERSAL 16] IMPLICIT NULL (SIZE (1..maxCellInfoUTRA-r9)) OF CellInfoUTRA-TDD-r10

CellInfoUTRA-TDD-r10 ::=			[UNIVERSAL 16] IMPLICIT NULL {
	physCellId-r10						PhysCellIdUTRA-TDD,
	carrierFreq-r10						ARFCN-ValueUTRA,
	utra-BCCH-Container-r10				OCTET STRING
}

-- ASN1STOP

RRCConnectionRequest ::=			[UNIVERSAL 16] IMPLICIT NULL {
	criticalExtensions					CHOICE {
		rrcConnectionRequest-r8				RRCConnectionRequest-r8-IEs,
		criticalExtensionsFuture			[UNIVERSAL 16] IMPLICIT NULL {}
	}
}

RRCConnectionRequest-r8-IEs ::=		[UNIVERSAL 16] IMPLICIT NULL {
	ue-Identity							InitialUE-Identity,
	establishmentCause					EstablishmentCause,
	spare								BIT STRING (SIZE (1))
}

InitialUE-Identity ::=				CHOICE {
	s-TMSI								S-TMSI,
	randomValue							BIT STRING (SIZE (40))
}

EstablishmentCause ::=				ENUMERATED {
										emergency, highPriorityAccess, mt-Access, mo-Signalling,
										mo-Data, delayTolerantAccess-v1020, mo-VoiceCall-v1280, spare1}

-- ASN1STOP

RRCConnectionSetup ::=				[UNIVERSAL 16] IMPLICIT NULL {
	rrc-TransactionIdentifier			RRC-TransactionIdentifier,
	criticalExtensions					CHOICE {
		c1									CHOICE {
			rrcConnectionSetup-r8				RRCConnectionSetup-r8-IEs,
			spare7 NULL,
			spare6 NULL, spare5 NULL, spare4 NULL,
			spare3 NULL, spare2 NULL, spare1 NULL
		},
		criticalExtensionsFuture			[UNIVERSAL 16] IMPLICIT NULL {}
	}
}

RRCConnectionSetup-r8-IEs ::=		[UNIVERSAL 16] IMPLICIT NULL {
	radioResourceConfigDedicated		RadioResourceConfigDedicated,
	nonCriticalExtension				RRCConnectionSetup-v8a0-IEs			OPTIONAL
}

RRCConnectionSetup-v8a0-IEs ::= [UNIVERSAL 16] IMPLICIT NULL {
	lateNonCriticalExtension			OCTET STRING						OPTIONAL,
	nonCriticalExtension				[UNIVERSAL 16] IMPLICIT NULL {}							OPTIONAL
}

-- ASN1STOP

RRCConnectionSetupComplete ::=		[UNIVERSAL 16] IMPLICIT NULL {
	rrc-TransactionIdentifier			RRC-TransactionIdentifier,
	criticalExtensions					CHOICE {
		c1									CHOICE{
			rrcConnectionSetupComplete-r8		RRCConnectionSetupComplete-r8-IEs,
			spare3 NULL, spare2 NULL, spare1 NULL
		},
		criticalExtensionsFuture			[UNIVERSAL 16] IMPLICIT NULL {}
	}
}

RRCConnectionSetupComplete-r8-IEs ::= [UNIVERSAL 16] IMPLICIT NULL {
	selectedPLMN-Identity				INTEGER (1..maxPLMN-r11),
	registeredMME						RegisteredMME						OPTIONAL,
	dedicatedInfoNAS					DedicatedInfoNAS,
	nonCriticalExtension				RRCConnectionSetupComplete-v8a0-IEs	OPTIONAL
}

RRCConnectionSetupComplete-v8a0-IEs ::= [UNIVERSAL 16] IMPLICIT NULL {
	lateNonCriticalExtension			OCTET STRING						OPTIONAL,
	nonCriticalExtension				RRCConnectionSetupComplete-v1020-IEs	OPTIONAL
}

RRCConnectionSetupComplete-v1020-IEs ::= [UNIVERSAL 16] IMPLICIT NULL {
	gummei-Type-r10						ENUMERATED {native, mapped}			OPTIONAL,
	rlf-InfoAvailable-r10				ENUMERATED {true}					OPTIONAL,
	logMeasAvailable-r10				ENUMERATED {true}					OPTIONAL,
	rn-SubframeConfigReq-r10			ENUMERATED {required, notRequired}	OPTIONAL,
	nonCriticalExtension				RRCConnectionSetupComplete-v1130-IEs	OPTIONAL
}

RRCConnectionSetupComplete-v1130-IEs ::= [UNIVERSAL 16] IMPLICIT NULL {
	connEstFailInfoAvailable-r11		ENUMERATED {true}				OPTIONAL,
	nonCriticalExtension				RRCConnectionSetupComplete-v1250-IEs		OPTIONAL
}

RRCConnectionSetupComplete-v1250-IEs ::= [UNIVERSAL 16] IMPLICIT NULL {
	mobilityState-r12					ENUMERATED {normal, medium, high, spare}	OPTIONAL,
	mobilityHistoryAvail-r12			ENUMERATED {true}				OPTIONAL,
	logMeasAvailableMBSFN-r12			ENUMERATED {true}				OPTIONAL,
	nonCriticalExtension				[UNIVERSAL 16] IMPLICIT NULL {}						OPTIONAL
}

RegisteredMME ::=					[UNIVERSAL 16] IMPLICIT NULL {
	plmn-Identity						PLMN-Identity						OPTIONAL,
	mmegi								BIT STRING (SIZE (16)),
	mmec								MMEC
}

-- ASN1STOP

SCGFailureInformation-r12 ::=		[UNIVERSAL 16] IMPLICIT NULL {
	criticalExtensions					CHOICE {
		c1									CHOICE {
			scgFailureInformation-r12			SCGFailureInformation-r12-IEs,
			spare3 NULL, spare2 NULL, spare1 NULL
		},
		criticalExtensionsFuture			[UNIVERSAL 16] IMPLICIT NULL {}
	}
}

SCGFailureInformation-r12-IEs ::=	[UNIVERSAL 16] IMPLICIT NULL {
	failureReportSCG-r12				FailureReportSCG-r12 			OPTIONAL,
	nonCriticalExtension				[UNIVERSAL 16] IMPLICIT NULL {}							OPTIONAL
}

FailureReportSCG-r12 ::= 			[UNIVERSAL 16] IMPLICIT NULL {
	failureType-r12						ENUMERATED {t313-Expiry, randomAccessProblem,
												rlc-MaxNumRetx, scg-ChangeFailure },
	measResultServFreqList-r12			MeasResultServFreqList-r10		OPTIONAL,
	measResultNeighCells-r12			MeasResultList2EUTRA-r9			OPTIONAL,
--	...,
--	[[
	measResultServFreqListExt-r13			MeasResultServFreqListExt-r13		OPTIONAL
--	]]
}

-- ASN1STOP

SCPTMConfiguration-r13 ::=		[UNIVERSAL 16] IMPLICIT NULL {
	sc-mtch-InfoList-r13			SC-MTCH-InfoList-r13,
	scptmNeighbourCellList-r13		SCPTMNeighbourCellList-r13			OPTIONAL,
	...
}

-- ASN1STOP

SecurityModeCommand ::=				[UNIVERSAL 16] IMPLICIT NULL {
	rrc-TransactionIdentifier			RRC-TransactionIdentifier,
	criticalExtensions					CHOICE {
		c1									CHOICE{
			securityModeCommand-r8				SecurityModeCommand-r8-IEs,
			spare3 NULL, spare2 NULL, spare1 NULL
		},
		criticalExtensionsFuture			[UNIVERSAL 16] IMPLICIT NULL {}
	}
}

SecurityModeCommand-r8-IEs ::=		[UNIVERSAL 16] IMPLICIT NULL {
	securityConfigSMC					SecurityConfigSMC,
	nonCriticalExtension				SecurityModeCommand-v8a0-IEs		OPTIONAL
}

SecurityModeCommand-v8a0-IEs ::= [UNIVERSAL 16] IMPLICIT NULL {
	lateNonCriticalExtension			OCTET STRING						OPTIONAL,
	nonCriticalExtension				[UNIVERSAL 16] IMPLICIT NULL {}							OPTIONAL
}

SecurityConfigSMC ::=					[UNIVERSAL 16] IMPLICIT NULL {
	securityAlgorithmConfig					SecurityAlgorithmConfig,
	...
}

-- ASN1STOP

SecurityModeComplete ::=			[UNIVERSAL 16] IMPLICIT NULL {
	rrc-TransactionIdentifier			RRC-TransactionIdentifier,
	criticalExtensions					CHOICE {
		securityModeComplete-r8				SecurityModeComplete-r8-IEs,
		criticalExtensionsFuture			[UNIVERSAL 16] IMPLICIT NULL {}
	}
}

SecurityModeComplete-r8-IEs ::=		[UNIVERSAL 16] IMPLICIT NULL {
	nonCriticalExtension				SecurityModeComplete-v8a0-IEs							OPTIONAL
}

SecurityModeComplete-v8a0-IEs ::= [UNIVERSAL 16] IMPLICIT NULL {
	lateNonCriticalExtension			OCTET STRING						OPTIONAL,
	nonCriticalExtension				[UNIVERSAL 16] IMPLICIT NULL {}							OPTIONAL
}

-- ASN1STOP

SecurityModeFailure ::=				[UNIVERSAL 16] IMPLICIT NULL {
	rrc-TransactionIdentifier			RRC-TransactionIdentifier,
	criticalExtensions					CHOICE {
		securityModeFailure-r8				SecurityModeFailure-r8-IEs,
		criticalExtensionsFuture			[UNIVERSAL 16] IMPLICIT NULL {}
	}
}

SecurityModeFailure-r8-IEs ::=		[UNIVERSAL 16] IMPLICIT NULL {
	nonCriticalExtension				SecurityModeFailure-v8a0-IEs							OPTIONAL
}

SecurityModeFailure-v8a0-IEs ::= [UNIVERSAL 16] IMPLICIT NULL {
	lateNonCriticalExtension			OCTET STRING						OPTIONAL,
	nonCriticalExtension				[UNIVERSAL 16] IMPLICIT NULL {}							OPTIONAL
}

-- ASN1STOP

SidelinkUEInformation-r12 ::=		[UNIVERSAL 16] IMPLICIT NULL {
	criticalExtensions				CHOICE {
		c1								CHOICE {
			sidelinkUEInformation-r12		SidelinkUEInformation-r12-IEs,
			spare3 NULL, spare2 NULL, spare1 NULL
		},
		criticalExtensionsFuture			[UNIVERSAL 16] IMPLICIT NULL {}
	}
}

SidelinkUEInformation-r12-IEs ::=	[UNIVERSAL 16] IMPLICIT NULL {
	commRxInterestedFreq-r12		ARFCN-ValueEUTRA-r9			OPTIONAL,
	commTxResourceReq-r12			SL-CommTxResourceReq-r12	OPTIONAL,
	discRxInterest-r12				ENUMERATED {true}			OPTIONAL,
	discTxResourceReq-r12			INTEGER (1..63)				OPTIONAL,
	lateNonCriticalExtension		OCTET STRING				OPTIONAL,
	nonCriticalExtension			SidelinkUEInformation-v13x0-IEs	OPTIONAL
}

SidelinkUEInformation-v13x0-IEs ::=	[UNIVERSAL 16] IMPLICIT NULL {
	commTxResourceReq121-r13		SL-CommTxResourceReqUC-r13	OPTIONAL,
	commTxResourceInfoReqRelay-r13		[UNIVERSAL 16] IMPLICIT NULL {
		commTxResourceReqRelay-r13		SL-CommTxResourceReqUC-r13,
		ue-Type-r13						ENUMERATED {relayUE, remoteUE}
	}															OPTIONAL,
	discTxResourceReq-v13x0			[UNIVERSAL 16] IMPLICIT NULL {
		carrierFreqDiscTx-r13			INTEGER (1..maxFreq),
		discTxResourceReqAddFreq-r13	SL-DiscTxResourceReqPerFreqList-r13	OPTIONAL
	}															OPTIONAL,
	discTxResourceReqPS-r13			SL-DiscTxResourceReq-r13	OPTIONAL,
	discRxGapReq-r13					SL-GapRequest-r13			OPTIONAL,
	discTxGapReq-r13					SL-GapRequest-r13			OPTIONAL,
	discSysInfoReportList-r13			SL-SysInfoReportList-r13	OPTIONAL,
	nonCriticalExtension			[UNIVERSAL 16] IMPLICIT NULL {}					OPTIONAL
}

SL-CommTxResourceReq-r12 ::=		[UNIVERSAL 16] IMPLICIT NULL {
	carrierFreq-r12					ARFCN-ValueEUTRA-r9			OPTIONAL,
	destinationInfoList-r12			SL-DestinationInfoList-r12
}

SL-CommTxResourceReqUC-r13 ::=		[UNIVERSAL 16] IMPLICIT NULL {
	carrierFreq-r13					ARFCN-ValueEUTRA-r9			OPTIONAL,
	destinationInfoListUC-r13			SL-DestinationInfoListUC-r13
}

SL-DiscTxResourceReqPerFreqList-r13 ::=	[UNIVERSAL 16] IMPLICIT NULL (SIZE (1..maxFreq)) OF SL-DiscTxResourceReq-r13

SL-DiscTxResourceReq-r13 ::=		[UNIVERSAL 16] IMPLICIT NULL {
	carrierFreq-r13					ARFCN-ValueEUTRA-r9			OPTIONAL,
	discTxResourceReq-r13			INTEGER (1..63)
}

SL-DestinationInfoList-r12 ::=	[UNIVERSAL 16] IMPLICIT NULL (SIZE (1..maxSL-Dest-r12)) OF SL-DestinationIdentity-r12

SL-DestinationIdentity-r12 ::=	BIT STRING (SIZE (24))

SL-DestinationInfoListUC-r13 ::=	SL-DestinationInfoList-r12

SL-SysInfoReportList-r13 ::=	[UNIVERSAL 16] IMPLICIT NULL (SIZE (1.. maxSL-DiscSysInfoReportFreq-r13)) OF SL-SysInfoReport-r13

-- ASN1STOP

SystemInformation ::=				[UNIVERSAL 16] IMPLICIT NULL {
	criticalExtensions					CHOICE {
		systemInformation-r8				SystemInformation-r8-IEs,
		criticalExtensionsFuture			[UNIVERSAL 16] IMPLICIT NULL {}
	}
}
SystemInformation-r8-IEs ::=		[UNIVERSAL 16] IMPLICIT NULL {
	sib-TypeAndInfo						[UNIVERSAL 16] IMPLICIT NULL (SIZE (1..maxSIB)) OF CHOICE {
		sib2								SystemInformationBlockType2,
		sib3								SystemInformationBlockType3,
		sib4								SystemInformationBlockType4,
		sib5								SystemInformationBlockType5,
		sib6								SystemInformationBlockType6,
		sib7								SystemInformationBlockType7,
		sib8								SystemInformationBlockType8,
		sib9								SystemInformationBlockType9,
		sib10								SystemInformationBlockType10,
		sib11								SystemInformationBlockType11,
	--	...,
		sib12-v920							SystemInformationBlockType12-r9,
		sib13-v920							SystemInformationBlockType13-r9,
		sib14-v1130							SystemInformationBlockType14-r11,
		sib15-v1130							SystemInformationBlockType15-r11,
		sib16-v1130							SystemInformationBlockType16-r11,
		sib17-v1250							SystemInformationBlockType17-r12,
		sib18-v1250							SystemInformationBlockType18-r12,
		sib19-v1250							SystemInformationBlockType19-r12,
		sib20-v13x0							SystemInformationBlockType20-r13
	},
	nonCriticalExtension				SystemInformation-v8a0-IEs			OPTIONAL
}

SystemInformation-v8a0-IEs ::= [UNIVERSAL 16] IMPLICIT NULL {
	lateNonCriticalExtension			OCTET STRING						OPTIONAL,
	nonCriticalExtension				[UNIVERSAL 16] IMPLICIT NULL {}							OPTIONAL
}

-- ASN1STOP

SystemInformationBlockType1 ::=		[UNIVERSAL 16] IMPLICIT NULL {
	cellAccessRelatedInfo				[UNIVERSAL 16] IMPLICIT NULL {
		plmn-IdentityList					PLMN-IdentityList,
		trackingAreaCode					TrackingAreaCode,
		cellIdentity						CellIdentity,
		cellBarred							ENUMERATED {barred, notBarred},
		intraFreqReselection				ENUMERATED {allowed, notAllowed},
		csg-Indication						BOOLEAN,
		csg-Identity						CSG-Identity			OPTIONAL	-- Need OR
	},
	cellSelectionInfo					[UNIVERSAL 16] IMPLICIT NULL {
		q-RxLevMin							Q-RxLevMin,
		q-RxLevMinOffset					INTEGER (1..8)			OPTIONAL	-- Need OP
	},
	p-Max								P-Max						OPTIONAL,			-- Need OP
	freqBandIndicator					FreqBandIndicator,
	schedulingInfoList					SchedulingInfoList,
	tdd-Config							TDD-Config					OPTIONAL,	-- Cond TDD
	si-WindowLength						ENUMERATED {
											ms1, ms2, ms5, ms10, ms15, ms20,
											ms40},
	systemInfoValueTag					INTEGER (0..31),
	nonCriticalExtension				SystemInformationBlockType1-v890-IEs	OPTIONAL
}

SystemInformationBlockType1-v890-IEs::=	[UNIVERSAL 16] IMPLICIT NULL {
	lateNonCriticalExtension			OCTET STRING (CONTAINING SystemInformationBlockType1-v8h0-IEs)			OPTIONAL,
	nonCriticalExtension				SystemInformationBlockType1-v920-IEs	OPTIONAL
}

-- Late non critical extensions
SystemInformationBlockType1-v8h0-IEs ::=	[UNIVERSAL 16] IMPLICIT NULL {
	multiBandInfoList					MultiBandInfoList		OPTIONAL,	-- Need OR
	nonCriticalExtension				SystemInformationBlockType1-v9e0-IEs	OPTIONAL
}

SystemInformationBlockType1-v9e0-IEs ::= [UNIVERSAL 16] IMPLICIT NULL {
	freqBandIndicator-v9e0				FreqBandIndicator-v9e0		OPTIONAL,	-- Cond FBI-max
	multiBandInfoList-v9e0				MultiBandInfoList-v9e0		OPTIONAL,	-- Cond mFBI-max
	nonCriticalExtension				SystemInformationBlockType1-v10j0-IEs	OPTIONAL
}

SystemInformationBlockType1-v10j0-IEs ::= [UNIVERSAL 16] IMPLICIT NULL {
	freqBandInfo-r10					NS-PmaxList-r10				OPTIONAL,	-- Need OR
	multiBandInfoList-v10j0				MultiBandInfoList-v10j0		OPTIONAL,	-- Need OR
	nonCriticalExtension				[UNIVERSAL 16] IMPLICIT NULL {}					OPTIONAL
}

-- Regular non critical extensions
SystemInformationBlockType1-v920-IEs ::=	[UNIVERSAL 16] IMPLICIT NULL {
	ims-EmergencySupport-r9				ENUMERATED {true}			OPTIONAL,	-- Need OR
	cellSelectionInfo-v920				CellSelectionInfo-v920		OPTIONAL,	-- Cond RSRQ
	nonCriticalExtension				SystemInformationBlockType1-v1130-IEs	OPTIONAL
}

SystemInformationBlockType1-v1130-IEs ::=	[UNIVERSAL 16] IMPLICIT NULL {
	tdd-Config-v1130				TDD-Config-v1130			OPTIONAL,	-- Cond TDD-OR
	cellSelectionInfo-v1130			CellSelectionInfo-v1130		OPTIONAL,	-- Cond WB-RSRQ
	nonCriticalExtension			SystemInformationBlockType1-v1250-IEs	OPTIONAL
}

SystemInformationBlockType1-v1250-IEs ::=	[UNIVERSAL 16] IMPLICIT NULL {
	cellAccessRelatedInfo-v1250					[UNIVERSAL 16] IMPLICIT NULL {
		category0Allowed-r12						ENUMERATED {true}		OPTIONAL	-- Need OP
	},
	cellSelectionInfo-v1250					CellSelectionInfo-v1250		OPTIONAL,	-- Cond RSRQ2
	freqBandIndicatorPriority-r12			ENUMERATED {true}			OPTIONAL,	-- Cond mFBI
	nonCriticalExtension			SystemInformationBlockType1-v13xy-IEs	OPTIONAL				
}

SystemInformationBlockType1-v13xy-IEs ::=	[UNIVERSAL 16] IMPLICIT NULL {
	hyperSFN						BIT STRING (SIZE (10))		OPTIONAL,
	eDRXAllowed			ENUMERATED {true}		OPTIONAL, 
	nonCriticalExtension			[UNIVERSAL 16] IMPLICIT NULL {}					OPTIONAL
}

PLMN-IdentityList ::=					[UNIVERSAL 16] IMPLICIT NULL (SIZE (1..maxPLMN-r11)) OF PLMN-IdentityInfo

PLMN-IdentityInfo ::=					[UNIVERSAL 16] IMPLICIT NULL {
	plmn-Identity							PLMN-Identity,
	cellReservedForOperatorUse				ENUMERATED {reserved, notReserved}
}

SchedulingInfoList ::= [UNIVERSAL 16] IMPLICIT NULL (SIZE (1..maxSI-Message)) OF SchedulingInfo

SchedulingInfo ::=	[UNIVERSAL 16] IMPLICIT NULL {
	si-Periodicity						ENUMERATED {
											rf8, rf16, rf32, rf64, rf128, rf256, rf512},
	sib-MappingInfo						SIB-MappingInfo
}

SIB-MappingInfo ::= [UNIVERSAL 16] IMPLICIT NULL (SIZE (0..maxSIB-1)) OF SIB-Type

SIB-Type ::=						ENUMERATED {
										sibType3, sibType4, sibType5, sibType6,
										sibType7, sibType8, sibType9, sibType10,
										sibType11, sibType12-v920, sibType13-v920,
										sibType14-v1130, sibType15-v1130,
										sibType16-v1130, sibType17-v1250, sibType18-v1250,
										..., sibType19-v1250, sibType20-v13xy }

CellSelectionInfo-v920 ::=			[UNIVERSAL 16] IMPLICIT NULL {
	q-QualMin-r9						Q-QualMin-r9,
	q-QualMinOffset-r9					INTEGER (1..8)						OPTIONAL	-- Need OP
}

CellSelectionInfo-v1130 ::=			[UNIVERSAL 16] IMPLICIT NULL {
	q-QualMinWB-r11						Q-QualMin-r9
}

CellSelectionInfo-v1250 ::=			[UNIVERSAL 16] IMPLICIT NULL {
	q-QualMinRSRQ-OnAllSymbols-r12						Q-QualMin-r9
}

-- ASN1STOP

UEAssistanceInformation-r11 ::=				[UNIVERSAL 16] IMPLICIT NULL {
	criticalExtensions					CHOICE {
		c1									CHOICE {
			ueAssistanceInformation-r11			UEAssistanceInformation-r11-IEs,
			spare3 NULL, spare2 NULL, spare1 NULL
		},
		criticalExtensionsFuture			[UNIVERSAL 16] IMPLICIT NULL {}
	}
}

UEAssistanceInformation-r11-IEs ::=		[UNIVERSAL 16] IMPLICIT NULL {
	powerPrefIndication-r11				ENUMERATED	{normal, lowPowerConsumption}	OPTIONAL,
	lateNonCriticalExtension			OCTET STRING						OPTIONAL,
	nonCriticalExtension				[UNIVERSAL 16] IMPLICIT NULL {}							OPTIONAL
}

-- ASN1STOP

UECapabilityEnquiry ::=				[UNIVERSAL 16] IMPLICIT NULL {
	rrc-TransactionIdentifier			RRC-TransactionIdentifier,
	criticalExtensions					CHOICE {
		c1									CHOICE {
			ueCapabilityEnquiry-r8				UECapabilityEnquiry-r8-IEs,
			spare3 NULL, spare2 NULL, spare1 NULL
		},
		criticalExtensionsFuture			[UNIVERSAL 16] IMPLICIT NULL {}
	}
}

UECapabilityEnquiry-r8-IEs ::=		[UNIVERSAL 16] IMPLICIT NULL {
	ue-CapabilityRequest				UE-CapabilityRequest,
	nonCriticalExtension				UECapabilityEnquiry-v8a0-IEs		OPTIONAL
}

UECapabilityEnquiry-v8a0-IEs ::= [UNIVERSAL 16] IMPLICIT NULL {
	lateNonCriticalExtension			OCTET STRING						OPTIONAL,
	nonCriticalExtension				UECapabilityEnquiry-v1180-IEs							OPTIONAL
}

UECapabilityEnquiry-v1180-IEs ::= [UNIVERSAL 16] IMPLICIT NULL {
	requestedFrequencyBands-r11			[UNIVERSAL 16] IMPLICIT NULL (SIZE (1..16)) OF FreqBandIndicator-r11							OPTIONAL,
	nonCriticalExtension				UECapabilityEnquiry-v13xy-IEs 							OPTIONAL
}

UECapabilityEnquiry-v13xy-IEs ::= [UNIVERSAL 16] IMPLICIT NULL {
	requestReducedFormat-r13			ENUMERATED {true}					OPTIONAL,
	skipFallbackCombinations-r13		ENUMERATED {true}					OPTIONAL,
	requestedMaxCCsDL-r13			INTEGER (2..32)						OPTIONAL,
	requestedMaxCCsUL-r13			INTEGER (2..32)						OPTIONAL,
	nonCriticalExtension				[UNIVERSAL 16] IMPLICIT NULL {}							OPTIONAL
}

UE-CapabilityRequest ::=		[UNIVERSAL 16] IMPLICIT NULL (SIZE (1..maxRAT-Capabilities)) OF RAT-Type

-- ASN1STOP

UECapabilityInformation ::=			[UNIVERSAL 16] IMPLICIT NULL {
	rrc-TransactionIdentifier			RRC-TransactionIdentifier,
	criticalExtensions					CHOICE {
		c1									CHOICE{
			ueCapabilityInformation-r8			UECapabilityInformation-r8-IEs,
			spare7 NULL,
			spare6 NULL, spare5 NULL, spare4 NULL,
			spare3 NULL, spare2 NULL, spare1 NULL
		},
		criticalExtensionsFuture			[UNIVERSAL 16] IMPLICIT NULL {}
	}
}

UECapabilityInformation-r8-IEs ::=	[UNIVERSAL 16] IMPLICIT NULL {
	ue-CapabilityRAT-ContainerList		UE-CapabilityRAT-ContainerList,
	nonCriticalExtension				UECapabilityInformation-v8a0-IEs	OPTIONAL
}

UECapabilityInformation-v8a0-IEs ::= [UNIVERSAL 16] IMPLICIT NULL {
	lateNonCriticalExtension			OCTET STRING						OPTIONAL,
	nonCriticalExtension				UECapabilityInformation-v1250-IEs	OPTIONAL
}

UECapabilityInformation-v1250-IEs ::= [UNIVERSAL 16] IMPLICIT NULL {
	ue-RadioPagingInfo-r12				UE-RadioPagingInfo-r12				OPTIONAL,
	nonCriticalExtension				[UNIVERSAL 16] IMPLICIT NULL {}							OPTIONAL
}

-- ASN1STOP

UEInformationRequest-r9		::=				[UNIVERSAL 16] IMPLICIT NULL {
	rrc-TransactionIdentifier		RRC-TransactionIdentifier,
	criticalExtensions				CHOICE {
		c1								CHOICE {
			ueInformationRequest-r9				UEInformationRequest-r9-IEs,
			spare3 NULL, spare2 NULL, spare1 NULL
		},
		criticalExtensionsFuture			[UNIVERSAL 16] IMPLICIT NULL {}
	}
}

UEInformationRequest-r9-IEs ::=		[UNIVERSAL 16] IMPLICIT NULL {
	rach-ReportReq-r9					BOOLEAN,
	rlf-ReportReq-r9					BOOLEAN,
	nonCriticalExtension				UEInformationRequest-v930-IEs		OPTIONAL
}

UEInformationRequest-v930-IEs ::= [UNIVERSAL 16] IMPLICIT NULL {
	lateNonCriticalExtension			OCTET STRING						OPTIONAL,
	nonCriticalExtension				UEInformationRequest-v1020-IEs		OPTIONAL
}

UEInformationRequest-v1020-IEs ::=	[UNIVERSAL 16] IMPLICIT NULL {
	logMeasReportReq-r10				ENUMERATED {true}					OPTIONAL,	-- Need ON
	nonCriticalExtension				UEInformationRequest-v1130-IEs		OPTIONAL
}

UEInformationRequest-v1130-IEs ::= [UNIVERSAL 16] IMPLICIT NULL {
	connEstFailReportReq-r11			ENUMERATED {true}					OPTIONAL,	-- Need ON
	nonCriticalExtension				UEInformationRequest-v1250-IEs		OPTIONAL
}

UEInformationRequest-v1250-IEs ::= [UNIVERSAL 16] IMPLICIT NULL {
	mobilityHistoryReportReq-r12		ENUMERATED {true}					OPTIONAL,	-- Need ON
	nonCriticalExtension				[UNIVERSAL 16] IMPLICIT NULL {}							OPTIONAL
}

-- ASN1STOP

UEInformationResponse-r9	::=			[UNIVERSAL 16] IMPLICIT NULL {
	rrc-TransactionIdentifier			RRC-TransactionIdentifier,
	criticalExtensions					CHOICE {
		c1								CHOICE {
			ueInformationResponse-r9				UEInformationResponse-r9-IEs,
			spare3 NULL, spare2 NULL, spare1 NULL
		},
		criticalExtensionsFuture				[UNIVERSAL 16] IMPLICIT NULL {}
	}
}

UEInformationResponse-r9-IEs ::=		[UNIVERSAL 16] IMPLICIT NULL {
	rach-Report-r9							[UNIVERSAL 16] IMPLICIT NULL {
		numberOfPreamblesSent-r9				NumberOfPreamblesSent-r11,
		contentionDetected-r9					BOOLEAN
	}																OPTIONAL,
	rlf-Report-r9							RLF-Report-r9			OPTIONAL,
	nonCriticalExtension					UEInformationResponse-v930-IEs				OPTIONAL
}

-- Late non critical extensions
UEInformationResponse-v9e0-IEs ::= [UNIVERSAL 16] IMPLICIT NULL {
	rlf-Report-v9e0						RLF-Report-v9e0					OPTIONAL,
	nonCriticalExtension				[UNIVERSAL 16] IMPLICIT NULL {}						OPTIONAL
}

-- Regular non critical extensions
UEInformationResponse-v930-IEs ::=	[UNIVERSAL 16] IMPLICIT NULL {
	lateNonCriticalExtension			OCTET STRING (CONTAINING UEInformationResponse-v9e0-IEs)	OPTIONAL,
	nonCriticalExtension				UEInformationResponse-v1020-IEs		OPTIONAL
}

UEInformationResponse-v1020-IEs ::= [UNIVERSAL 16] IMPLICIT NULL {
	logMeasReport-r10					LogMeasReport-r10				OPTIONAL,
	nonCriticalExtension				UEInformationResponse-v1130-IEs		OPTIONAL
}

UEInformationResponse-v1130-IEs ::= [UNIVERSAL 16] IMPLICIT NULL {
	connEstFailReport-r11				ConnEstFailReport-r11			OPTIONAL,
	nonCriticalExtension				UEInformationResponse-v1250-IEs	OPTIONAL
}

UEInformationResponse-v1250-IEs ::= [UNIVERSAL 16] IMPLICIT NULL {
	mobilityHistoryReport-r12			MobilityHistoryReport-r12		OPTIONAL,
	nonCriticalExtension				[UNIVERSAL 16] IMPLICIT NULL {}						OPTIONAL
}

RLF-Report-r9 ::= 					[UNIVERSAL 16] IMPLICIT NULL {
	measResultLastServCell-r9				[UNIVERSAL 16] IMPLICIT NULL {
		rsrpResult-r9							RSRP-Range,
		rsrqResult-r9							RSRQ-Range			OPTIONAL
	},
	measResultNeighCells-r9				[UNIVERSAL 16] IMPLICIT NULL {
		measResultListEUTRA-r9				MeasResultList2EUTRA-r9			OPTIONAL,
		measResultListUTRA-r9				MeasResultList2UTRA-r9			OPTIONAL,
		measResultListGERAN-r9				MeasResultListGERAN				OPTIONAL,
		measResultsCDMA2000-r9				MeasResultList2CDMA2000-r9		OPTIONAL
	}	OPTIONAL,
	...,
--	[[	
	locationInfo-r10				LocationInfo-r10		OPTIONAL,
		failedPCellId-r10						CHOICE {
			cellGlobalId-r10						CellGlobalIdEUTRA,
			pci-arfcn-r10							[UNIVERSAL 16] IMPLICIT NULL {
				physCellId-r10							PhysCellId,
				carrierFreq-r10							ARFCN-ValueEUTRA
			}
		}																OPTIONAL,
		reestablishmentCellId-r10		CellGlobalIdEUTRA				OPTIONAL,
		timeConnFailure-r10				INTEGER (0..1023)				OPTIONAL,
		connectionFailureType-r10		ENUMERATED {rlf, hof}			OPTIONAL,
		previousPCellId-r10				CellGlobalIdEUTRA				OPTIONAL
--	]]
	,
--	[[	
                failedPCellId-v1090				[UNIVERSAL 16] IMPLICIT NULL {
			carrierFreq-v1090				ARFCN-ValueEUTRA-v9e0
		}																OPTIONAL
--	]],
        ,
--	[[
            basicFields-r11					[UNIVERSAL 16] IMPLICIT NULL {
			c-RNTI-r11						C-RNTI,
			rlf-Cause-r11					ENUMERATED {
												t310-Expiry, randomAccessProblem,
												rlc-MaxNumRetx, t312-Expiry-r12},
			timeSinceFailure-r11			TimeSinceFailure-r11
		}																OPTIONAL,
		previousUTRA-CellId-r11			[UNIVERSAL 16] IMPLICIT NULL {
			carrierFreq-r11					ARFCN-ValueUTRA,
			physCellId-r11					CHOICE {
				fdd-r11							PhysCellIdUTRA-FDD,
				tdd-r11							PhysCellIdUTRA-TDD
			},
			cellGlobalId-r11				CellGlobalIdUTRA			OPTIONAL
		}																OPTIONAL,
		selectedUTRA-CellId-r11			[UNIVERSAL 16] IMPLICIT NULL {
			carrierFreq-r11					ARFCN-ValueUTRA,
			physCellId-r11					CHOICE {
				fdd-r11							PhysCellIdUTRA-FDD,
				tdd-r11							PhysCellIdUTRA-TDD
			}
		}																OPTIONAL
--	]]
,
--	[[\n	
                failedPCellId-v1250				[UNIVERSAL 16] IMPLICIT NULL {
			tac-FailedPCell-r12			TrackingAreaCode				
		}																OPTIONAL,
		measResultLastServCell-v1250	RSRQ-Range-v1250				OPTIONAL,
		lastServCellRSRQ-Type-r12		RSRQ-Type-r12					OPTIONAL,
		measResultListEUTRA-v1250		MeasResultList2EUTRA-v1250		OPTIONAL
--	]]
,
--	[[
	droppedQCI-r13					ENUMERATED {qci1}				OPTIONAL
--	]]
}

RLF-Report-v9e0 ::= 				[UNIVERSAL 16] IMPLICIT NULL {
	measResultListEUTRA-v9e0			MeasResultList2EUTRA-v9e0
}

MeasResultList2EUTRA-r9 ::=				[UNIVERSAL 16] IMPLICIT NULL (SIZE (1..maxFreq)) OF MeasResult2EUTRA-r9

MeasResultList2EUTRA-v9e0 ::=			[UNIVERSAL 16] IMPLICIT NULL (SIZE (1..maxFreq)) OF MeasResult2EUTRA-v9e0

MeasResultList2EUTRA-v1250 ::=			[UNIVERSAL 16] IMPLICIT NULL (SIZE (1..maxFreq)) OF MeasResult2EUTRA-v1250

MeasResult2EUTRA-r9 ::=				[UNIVERSAL 16] IMPLICIT NULL {
	carrierFreq-r9						ARFCN-ValueEUTRA,
	measResultList-r9					MeasResultListEUTRA
}

MeasResult2EUTRA-v9e0 ::=				[UNIVERSAL 16] IMPLICIT NULL {
	carrierFreq-v9e0						ARFCN-ValueEUTRA-v9e0		OPTIONAL
}

MeasResult2EUTRA-v1250 ::=				[UNIVERSAL 16] IMPLICIT NULL {
	rsrq-Type-r12							RSRQ-Type-r12		OPTIONAL
}

MeasResultList2UTRA-r9 ::=			[UNIVERSAL 16] IMPLICIT NULL (SIZE (1..maxFreq)) OF MeasResult2UTRA-r9

MeasResult2UTRA-r9 ::=				[UNIVERSAL 16] IMPLICIT NULL {
	carrierFreq-r9						ARFCN-ValueUTRA,
	measResultList-r9					MeasResultListUTRA
}

MeasResultList2CDMA2000-r9 ::=		[UNIVERSAL 16] IMPLICIT NULL (SIZE (1..maxFreq)) OF MeasResult2CDMA2000-r9

MeasResult2CDMA2000-r9 ::= 			[UNIVERSAL 16] IMPLICIT NULL {
	carrierFreq-r9						CarrierFreqCDMA2000,
	measResultList-r9					MeasResultsCDMA2000
}

LogMeasReport-r10 ::= 				[UNIVERSAL 16] IMPLICIT NULL {
	absoluteTimeStamp-r10				AbsoluteTimeInfo-r10,
	traceReference-r10					TraceReference-r10,
	traceRecordingSessionRef-r10		OCTET STRING (SIZE (2)),
	tce-Id-r10							OCTET STRING (SIZE (1)),
	logMeasInfoList-r10					LogMeasInfoList-r10,
	logMeasAvailable-r10				ENUMERATED {true}				OPTIONAL
}

END
